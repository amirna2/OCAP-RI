OC-HOME-NETWORK-MIB DEFINITIONS ::= BEGIN

IMPORTS
    OBJECT-GROUP,
    MODULE-COMPLIANCE
        FROM SNMPv2-CONF              -- RFC 2580
    Integer32,
    Unsigned32,
    Counter32,
    OBJECT-TYPE,
    MODULE-IDENTITY
        FROM SNMPv2-SMI               -- RFC 2578
    TruthValue,
    RowStatus,
    MacAddress,
    TEXTUAL-CONVENTION
        FROM SNMPv2-TC                -- RFC 2579
    SnmpAdminString
        FROM SNMP-FRAMEWORK-MIB       -- RFC 3411
    InetAddressType,
    InetPortNumber,
    InetAddress
        FROM INET-ADDRESS-MIB         -- RFC 4001
    clabProjOpenCable
        FROM CLAB-DEF-MIB
    ifIndex
        FROM IF-MIB
        ;

ocHnMibModule MODULE-IDENTITY
    LAST-UPDATED "201009100000Z"        -- September 10, 2010
    ORGANIZATION "Cable Television Laboratories, Inc."
    CONTACT-INFO
         "Postal: Cable Television Laboratories, Inc.
         858 Coal Creek Circle
         Louisville, Colorado 80027-9750
         U.S.A.
         Phone:  +1 303-661-9100
         Fax:    +1 303-661-9199
         E-mail: mibs@cablelabs.com"
    DESCRIPTION
            "This MIB module contains the objects for the
            management of an OpenCable Home Network. The 
            MIB resides on the OpenCable Host Device if the
            Home Network Extension is implemented."
    REVISION "201202010000Z"            -- February 1, 2012
    DESCRIPTION
            "Added VPOP configuration object, 
            ocHnNetConfigViewPrimaryOutputPort "
    REVISION "201009100000Z"            -- September 10, 2010
    DESCRIPTION
            "Added static PQoS configuration parameter and
            associated table."
    REVISION "201005070000Z"            -- May 7, 2010
    DESCRIPTION
            "Added device properties group."
    REVISION "200909210000Z"            -- September 21, 2009
    DESCRIPTION
            "This version is being published as part of the 
            OpenCable Home Networking MIB specification I01."
    ::= { clabProjOpenCable 2 }

Tenths ::= TEXTUAL-CONVENTION
    DISPLAY-HINT "d-1"
    STATUS      current
    DESCRIPTION
            "This data type represents generic decimal units
            in Tenths. For example, a value of 5.1 will be
            represented as 51."
    SYNTAX      Integer32

PowerUnit ::= TEXTUAL-CONVENTION
    STATUS      current
    DESCRIPTION
            "Represents a well-known RSD power unit of 
            measurement."
    SYNTAX      INTEGER { 
                         other(1),
                         dBmV(2),
                         dBm(3),
                         mW(4)
                        }

--
-- Node definitions
--

ocHnNotifications OBJECT IDENTIFIER ::= { ocHnMibModule 1 }
ocHnMibObjects    OBJECT IDENTIFIER ::= { ocHnMibModule 2 }

ocHnHomeNetStatus OBJECT IDENTIFIER ::= { ocHnMibObjects 1 }

--
-- Reserved Services Domain Status
--

ocHnRsdManagerStatus OBJECT IDENTIFIER ::= { ocHnHomeNetStatus 1 }

ocHnRsdManagerImportanceNumber OBJECT-TYPE
    SYNTAX      Unsigned32 (0..255)
    MAX-ACCESS  read-write
    STATUS      current
    DESCRIPTION
            "Configurable importance number for the RSDManager in 
            this device. Used to determine the preferred RSDManager
            on the home network."
    ::= { ocHnRsdManagerStatus 1 }

ocHnRsdManagerPreferredStatus OBJECT-TYPE
    SYNTAX      TruthValue
    MAX-ACCESS  read-only
    STATUS      current
    DESCRIPTION
            "True indicates this is the preferred RSD Manager
            on the home network."
    ::= { ocHnRsdManagerStatus 2 }

--
-- UPnP Services Status information
--

ocHnDevUpnpServiceTable OBJECT-TYPE
    SYNTAX      SEQUENCE OF OcHnDevUpnpServiceEntry
    MAX-ACCESS  not-accessible
    STATUS      current
    DESCRIPTION
            "This table defines each service offered
            by this device. One row should be created
            for each supported service."
    ::= { ocHnHomeNetStatus 2 }

ocHnDevUpnpServiceEntry OBJECT-TYPE
    SYNTAX      OcHnDevUpnpServiceEntry
    MAX-ACCESS  not-accessible
    STATUS      current
    DESCRIPTION
            "Each entry defines a UPnP service."
    INDEX { ocHnDevUpnpServiceIndex }
    ::= { ocHnDevUpnpServiceTable 1 }

OcHnDevUpnpServiceEntry ::=
    SEQUENCE {
        ocHnDevUpnpServiceIndex
            Unsigned32,
        ocHnDevUpnpServiceType
            INTEGER,
        ocHnDevUpnpServiceAvailable
            TruthValue
        }

ocHnDevUpnpServiceIndex OBJECT-TYPE
    SYNTAX      Unsigned32 (1..4294967295)
    MAX-ACCESS  not-accessible
    STATUS      current
    DESCRIPTION
            "Table Index."
    ::= { ocHnDevUpnpServiceEntry 1 }

ocHnDevUpnpServiceType OBJECT-TYPE
    SYNTAX      INTEGER {
                        cds(1),
                        srs(2),
                        qosManager(3),
                        qosDevice(4),
                        qosPolicyHolder(5),
                        avt(6),
                        cm(7),
                        rcs(8)
                        }
    MAX-ACCESS  read-only
    STATUS      current
    DESCRIPTION
            "Service options currently available."
    ::= { ocHnDevUpnpServiceEntry 2 }

ocHnDevUpnpServiceAvailable OBJECT-TYPE
    SYNTAX      TruthValue
    MAX-ACCESS  read-only
    STATUS      current
    DESCRIPTION
            "Service is available (true) or unavailable (false)."
    ::= { ocHnDevUpnpServiceEntry 3 }

--
-- Supported Channels Table
--

ocHnDevSupportedChannelTable OBJECT-TYPE
    SYNTAX      SEQUENCE OF OcHnDevSupportedChannelEntry
    MAX-ACCESS  not-accessible
    STATUS      current
    DESCRIPTION
            "This table identifies the RSD Technology channels
            for each interface supported by a particular RSD node.
            This table is required for RF-based technologies."
    ::= { ocHnHomeNetStatus 3 }

ocHnDevSupportedChannelEntry OBJECT-TYPE
    SYNTAX      OcHnDevSupportedChannelEntry
    MAX-ACCESS  not-accessible
    STATUS      current
    DESCRIPTION
            "Each entry defines an offered channel by interface."
    INDEX { ifIndex, ocHnDevSupportedChannelIndex }
    ::= { ocHnDevSupportedChannelTable 1 }

OcHnDevSupportedChannelEntry ::=
    SEQUENCE {
        ocHnDevSupportedChannelIndex
            Unsigned32,
        ocHnDevSupportedChannelLastOperatingFreq
            TruthValue,
        ocHnDevSupportedChannelInUse
            TruthValue,
        ocHnDevSupportedChannelFrequency
            Unsigned32,
        ocHnDevSupportedChannelEligible
            TruthValue
        }

ocHnDevSupportedChannelIndex OBJECT-TYPE
    SYNTAX      Unsigned32 (1..4294967295)
    MAX-ACCESS  not-accessible
    STATUS      current
    DESCRIPTION
            "Index for each channel supported by the
            interface indicated by the ifIndex."
    ::= { ocHnDevSupportedChannelEntry 1 }

ocHnDevSupportedChannelLastOperatingFreq OBJECT-TYPE
    SYNTAX      TruthValue
    MAX-ACCESS  read-only
    STATUS      current
    DESCRIPTION
            "Indicates this channel/frequency
            was tuned when last in the LinkUp state.
            The value is persistent through reboots."
    ::= { ocHnDevSupportedChannelEntry 2 }

ocHnDevSupportedChannelInUse OBJECT-TYPE
    SYNTAX      TruthValue
    MAX-ACCESS  read-write
    STATUS      current
    DESCRIPTION
            "This channel is currently being used by
            this interface."
    ::= { ocHnDevSupportedChannelEntry 3 }

ocHnDevSupportedChannelFrequency OBJECT-TYPE
    SYNTAX      Unsigned32 (0..2000000000)
    UNITS       "hertz"
    MAX-ACCESS  read-only 
    STATUS      current
    DESCRIPTION
            "Channel center frequency. This channel must be available
            for selection as the operating frequency."
    ::= { ocHnDevSupportedChannelEntry 4 }

ocHnDevSupportedChannelEligible OBJECT-TYPE
    SYNTAX      TruthValue
    MAX-ACCESS  read-write
    STATUS      current
    DESCRIPTION
            "This channel is currently eligible for use."
    ::= { ocHnDevSupportedChannelEntry 5 }

--
--  Device Properties: Lists various UPnP Device properties
--

ocHnDevProperties OBJECT IDENTIFIER ::= { ocHnHomeNetStatus 4 }

ocHnDevPropertiesFriendlyName OBJECT-TYPE
    SYNTAX      SnmpAdminString
    MAX-ACCESS  read-only
    STATUS      current
    DESCRIPTION
            "Value from the <friendlyName> element in the OCAP Root 
            Device Description of the device as defined in Annex A
            of [HNP2.0]."
    ::= { ocHnDevProperties 1 }

--
-- Rotameter configuration options 
--

ocHnROConfiguration OBJECT IDENTIFIER ::= { ocHnMibObjects 2 }

ocHnRotameterConfigTable OBJECT-TYPE
    SYNTAX      SEQUENCE OF OcHnRotameterConfigEntry
    MAX-ACCESS  not-accessible
    STATUS      current
    DESCRIPTION
            "This table contains the basic rotameter observation 
            configuration parameters. Each row defines a set of 
            parameters to configure a rotameter observation. The 
            device may obtain per stream statistics, if requested,
            using one or more rows in the 
            PerStreamRotameterConfigTable."
    ::= { ocHnROConfiguration 1 }

ocHnRotameterConfigEntry OBJECT-TYPE
    SYNTAX      OcHnRotameterConfigEntry
    MAX-ACCESS  not-accessible
    STATUS      current
    DESCRIPTION
            "Each entry represents set of configuration parameters for
            one observation."
    INDEX { ocHnRotameterConfigIndex }
    ::= { ocHnRotameterConfigTable 1 }

OcHnRotameterConfigEntry ::=
    SEQUENCE {
              ocHnRotameterConfigIndex
                  Unsigned32,
              ocHnRotameterConfigRowStatus
                  RowStatus,
              ocHnRotameterConfigObservationActive
                  TruthValue,
              ocHnRotameterConfigPeriod
                  Unsigned32,
              ocHnRotameterConfigMonitorResolutionPeriod
                  Unsigned32,
             ocHnRotameterConfigQosSegmentId
                  OCTET STRING,
             ocHnRotameterConfigEndpointMacAddress
                  MacAddress
             }

ocHnRotameterConfigIndex OBJECT-TYPE
    SYNTAX      Unsigned32 (1..4294967295)
    MAX-ACCESS  not-accessible
    STATUS      current
    DESCRIPTION
            "Table Index."
    ::= { ocHnRotameterConfigEntry 1 }

ocHnRotameterConfigRowStatus OBJECT-TYPE
    SYNTAX      RowStatus
    MAX-ACCESS  read-create
    STATUS      current
    DESCRIPTION
            "Controls and reflects the status of rows in this
            Table (see RowStatus textual convention). There 
            is no restriction on changing any of the associated
            columns for this row while this object is set
            to active (i.e., columnar objects can be modified
            when the row is active). An active row does not
            equate to an active observation; it implies only that
            the rotameter observation can be initiated when 
            ocHnRotameterConfigObservationActive is set to 'True'."
    ::= { ocHnRotameterConfigEntry 2}

ocHnRotameterConfigObservationActive OBJECT-TYPE
    SYNTAX      TruthValue
    MAX-ACCESS  read-create
    STATUS      current
    DESCRIPTION
            "Setting this value to 'True' causes the rotameter to be
            configured and activated per the specified columns in 
            the row. Only one row observation can be active at any 
            given time."
    ::= { ocHnRotameterConfigEntry 3 }

ocHnRotameterConfigPeriod OBJECT-TYPE
    SYNTAX      Unsigned32
    MAX-ACCESS  read-create
    STATUS      current
    DESCRIPTION
            "This integer field specifies the duration in seconds 
            over which the Rotameter Observation is performed.
            This value must be less than or equal to the Monitoring
            Resolution Period. The default is 0 and indicates no
            monitoring."
    ::= { ocHnRotameterConfigEntry 4 }

ocHnRotameterConfigMonitorResolutionPeriod OBJECT-TYPE
    SYNTAX      Unsigned32
    MAX-ACCESS  read-create
    STATUS      current
    DESCRIPTION
            "This integer field specifies, in seconds, how often a 
            Rotameter observation is initiated. The default value 
            of 0 indicates no monitoring in progress."
    ::= { ocHnRotameterConfigEntry 5 }

ocHnRotameterConfigQosSegmentId OBJECT-TYPE
    SYNTAX       OCTET STRING
    MAX-ACCESS  read-create
    STATUS      current
    DESCRIPTION
            "This uniquely identifies a network segment of a shared
            Media technology. This parameter needs
            to be configured to obtain traffic statistics for a 
            specific QosSegment and for a specific traffic stream 
            identified by a combination of Layer2StreamId and a 
            QosSegmentId. The default value of 0 indicates no 
            QosSegment is specified."
    ::= { ocHnRotameterConfigEntry 6 }

ocHnRotameterConfigEndpointMacAddress OBJECT-TYPE
    SYNTAX      MacAddress
    MAX-ACCESS  read-create
    STATUS      current
    DESCRIPTION
           "This is an optional field. If value of all zeros is 
           provided, the device reports information about the traffic
           for the entire QosSegment identified by QosSegmentId.
           If non-zero value is provided, this device provides 
           information about traffic between its interface, identified
           by the ocHnQosROStatsMacAddress field and the device,
           identified by this parameter. If no value is specified,
           the device either reports traffic to/from itself or between
           itself and other devices on the network."
    ::= { ocHnRotameterConfigEntry 7 }

--
-- Rotameter augmentation table 
-- Use in conjunction with the OcHnRotameterConfigTable if 
-- stream-based observations are required 
--

ocHnPerStreamRotameterConfigTable OBJECT-TYPE
    SYNTAX      SEQUENCE OF OcHnPerStreamRotameterConfigEntry
    MAX-ACCESS  not-accessible
    STATUS      current
    DESCRIPTION
            "This table optionally augments the rotameter observation
            configuration parameters. Each row defines a set of
            parameters to configure a per-stream rotameter observation.
            Care must be taken when specifying both
            ocHnPerStreamRotameterConfigTrafficHandle and 
            ocHnPerStreamRotameterConfigLayer2StreamId parameters to 
            ensure that they both identify the same traffic stream."
    ::= { ocHnROConfiguration 2 }

ocHnPerStreamRotameterConfigEntry OBJECT-TYPE
    SYNTAX      OcHnPerStreamRotameterConfigEntry
    MAX-ACCESS  not-accessible
    STATUS      current
    DESCRIPTION
            "Each entry represents one stream traffic descriptor."
    INDEX { ocHnPerStreamRotameterConfigIndex, ocHnRotameterConfigIndex }
    ::= { ocHnPerStreamRotameterConfigTable 1 }

OcHnPerStreamRotameterConfigEntry ::=
    SEQUENCE {
              ocHnPerStreamRotameterConfigIndex
                  Unsigned32,
              ocHnPerStreamRotameterConfigRowStatus
                  RowStatus,
              ocHnPerStreamRotameterConfigLayer2StreamId
                  OCTET STRING,
              ocHnPerStreamRotameterConfigTrafficHandle
                  OCTET STRING,
              ocHnPerStreamRotameterConfigObservationActive
                  TruthValue
             }

ocHnPerStreamRotameterConfigIndex OBJECT-TYPE
    SYNTAX      Unsigned32 (1..4294967295)
    MAX-ACCESS  not-accessible
    STATUS      current
    DESCRIPTION
            "Table Index."
    ::= { ocHnPerStreamRotameterConfigEntry 1 }

ocHnPerStreamRotameterConfigRowStatus OBJECT-TYPE
    SYNTAX      RowStatus
    MAX-ACCESS  read-create
    STATUS      current
    DESCRIPTION
            "Controls and reflects the status of rows in this
            table (see RowStatus textual convention). There 
            is no restriction on changing any of the associated
            columns for this row while this object is set
            to active (i.e., columnar objects can be modified
            when the row is active)."
    ::= { ocHnPerStreamRotameterConfigEntry 2}

ocHnPerStreamRotameterConfigLayer2StreamId OBJECT-TYPE
    SYNTAX      OCTET STRING (SIZE (64) )
    MAX-ACCESS  read-create
    STATUS      current
    DESCRIPTION
            "This identifies a unique traffic stream flowing through a
            QoS segment identified by a QosSegmentId. A Control Point
            optionally specifies this field if it is interested in 
            obtaining information for a specific traffic stream 
            identified by a Layer2StreamId on the specified
            QosSegmentId. The default value of '0x00' indicates
            no ocHnRotameterLayer2StreamId specified."
    ::= { ocHnPerStreamRotameterConfigEntry 3 }

ocHnPerStreamRotameterConfigTrafficHandle OBJECT-TYPE
    SYNTAX      OCTET STRING 
    MAX-ACCESS  read-create
    STATUS      current
    DESCRIPTION
            "This identifies a unique UPnP traffic stream flowing
            through a device that supports a QosDevice service.
            A Control Point optionally specifies this field if it is
            interested in obtaining information for a specific UPnP
            traffic stream. The default value 'null' indicates
            no handle has been specified."
    ::= { ocHnPerStreamRotameterConfigEntry 4 }

ocHnPerStreamRotameterConfigObservationActive OBJECT-TYPE
    SYNTAX      TruthValue
    MAX-ACCESS  read-create
    STATUS      current
    DESCRIPTION
            "Setting this value to 'True' causes the rotameter to be
            configured per the specified columns in the row. Multiple
            rows in this table may be active concurrently to allow for
            multiple streams to be included in a single observation."
    ::= { ocHnPerStreamRotameterConfigEntry 5 }

ocHnQos OBJECT IDENTIFIER ::= { ocHnMibObjects 3 }

--
-- QoS stream, policy, and traffic configuration
-- for RSD Technologies only.

--
-- Dynamic configuration parameters
--

ocHnQosTrafficInfo OBJECT IDENTIFIER ::= { ocHnQos 1 }

ocHnQosStreamsInfoCollectionTrigger OBJECT-TYPE
    SYNTAX      TruthValue
    MAX-ACCESS  read-write
    STATUS      current
    DESCRIPTION
            "Setting to true(1) causes this device 
            to populate the ocHnQosTrafficDescTable with traffic
            descriptor information for each known stream established
            using UPnP QoS."
    ::= { ocHnQosTrafficInfo 1 }

--
-- QoS traffic descriptor table. Populated only when triggered 
-- by setting the ocHnQosStreamsInfoCollectionTrigger to true(1).
--

ocHnQosTrafficDescTable OBJECT-TYPE
    SYNTAX      SEQUENCE OF OcHnQosTrafficDescEntry
    MAX-ACCESS  not-accessible
    STATUS      current
    DESCRIPTION
            "This table contains the traffic descriptor information
            for each traffic stream established using UPnP QoS. It is
            populated only when directed to do so via the MIB object 
            ocHnQosStreamsInfoCollectionTrigger. Each invocation of
            the collection trigger will cause a refresh
            of these values."
    ::= { ocHnQosTrafficInfo 2 }

ocHnQosTrafficDescEntry OBJECT-TYPE
    SYNTAX      OcHnQosTrafficDescEntry
    MAX-ACCESS  not-accessible
    STATUS      current
    DESCRIPTION
            "Each entry represents one stream traffic descriptor."
    INDEX { ocHnQosTrafficDescIndex }
    ::= { ocHnQosTrafficDescTable 1 }

OcHnQosTrafficDescEntry ::=
    SEQUENCE {
        ocHnQosTrafficDescIndex
            Unsigned32,
        ocHnQosTrafficHandle
            OCTET STRING,
        ocHnQosTrafficQDMacAddress
            MacAddress,
        ocHnQosTrafficNetworkAddressType
            InetAddressType,
        ocHnQosTrafficSourceAddress
            InetAddress,
        ocHnQosTrafficSourcePort
            InetPortNumber,
        ocHnQosTrafficDestinationAddress
            InetAddress,
        ocHnQosTrafficDestinationPort
            InetPortNumber,
        ocHnQosTrafficIpProtocol
            Unsigned32,
        ocHnQosTrafficV3TrafficIdSourceUuid
            OCTET STRING,
        ocHnQosTrafficV3TrafficIdDestinationUuid
            OCTET STRING,
        ocHnQosTrafficMediaServerConnectionId
            Integer32,
        ocHnQosTrafficMediaRendererConnectionId
            Integer32,
        ocHnQosTrafficLeaseTime
            Unsigned32,
        ocHnQosTrafficCritical
            INTEGER,
        ocHnQosTrafficUserName
            SnmpAdminString,
        ocHnQosTrafficVendorApplicationName
            OCTET STRING, 
        ocHnQosTrafficPortName
            OCTET STRING, 
        ocHnQosTrafficServiceProviderServiceName
            OCTET STRING,
        ocHnQosTrafficCpName
            SnmpAdminString
        } 

ocHnQosTrafficDescIndex OBJECT-TYPE
    SYNTAX      Unsigned32 (1..4294967295)
    MAX-ACCESS  not-accessible
    STATUS      current
    DESCRIPTION
            "Table Index."
    ::= { ocHnQosTrafficDescEntry 1 }

ocHnQosTrafficHandle OBJECT-TYPE
    SYNTAX      OCTET STRING
    MAX-ACCESS  read-only
    STATUS      current
    DESCRIPTION
            "The unique identifier associated with a particular 
            instance of TrafficDescriptor (i.e., a particular
            traffic stream). This object serves as a secondary
            index into the related TSPEC table in which the active
            TSPEC is denoted."
    ::= { ocHnQosTrafficDescEntry 2 }

ocHnQosTrafficQDMacAddress OBJECT-TYPE
    SYNTAX      MacAddress
    MAX-ACCESS  read-only
    STATUS      current
    DESCRIPTION
            "Identifies a QoS Device in which the QoS
            Stream/flow was registered."
    ::= { ocHnQosTrafficDescEntry 3 }

ocHnQosTrafficNetworkAddressType OBJECT-TYPE
    SYNTAX      InetAddressType
    MAX-ACCESS  read-only
    STATUS      current
    DESCRIPTION
            "IP Address type for source and destination IP
            addresses in the traffic descriptors. 
            Textual convention will report IPv4(1) or
            IPv6(2)."
    ::= { ocHnQosTrafficDescEntry 4 }

ocHnQosTrafficSourceAddress OBJECT-TYPE
    SYNTAX      InetAddress
    MAX-ACCESS  read-only
    STATUS      current
    DESCRIPTION
            "Source IP address in traffic descriptor. A value
            of 0.0.0.0 (:: for IPv6) indicates 'do not care'. This must
            be consistent with the object 
            ocHnQosTrafficNetworkAddressType within a conceptual row."
    ::= { ocHnQosTrafficDescEntry 5 }

ocHnQosTrafficSourcePort OBJECT-TYPE
    SYNTAX      InetPortNumber
    MAX-ACCESS  read-only
    STATUS      current
    DESCRIPTION
            "Source protocol port number in traffic descriptor.
            A value of 0 represents a 'Don't Care', i.e., the 
            condition where a Control Point wants to set up 
            QoS for all traffic streams irrespective of the 
            SourcePort."
    ::= { ocHnQosTrafficDescEntry 6 }

ocHnQosTrafficDestinationAddress OBJECT-TYPE
    SYNTAX      InetAddress
    MAX-ACCESS  read-only
    STATUS      current
    DESCRIPTION
            "Destination IP address in traffic descriptor. A value
            of 0.0.0.0 (:: for IPv6)indicates 'do not care'. This
            must be consistent with the object
            ocHnQosTrafficNetworkAddressType."
    ::= { ocHnQosTrafficDescEntry 7 }

ocHnQosTrafficDestinationPort OBJECT-TYPE
    SYNTAX      InetPortNumber
    MAX-ACCESS  read-only
    STATUS      current
    DESCRIPTION
            "Destination protocol port number in traffic descriptor.
            A value of 0 represents a 'Don't Care', i.e., the 
            condition where a Control Point wants to set up 
            QoS for all traffic streams irrespective of the 
            DestinationPort."
    ::= { ocHnQosTrafficDescEntry 8 }

ocHnQosTrafficIpProtocol OBJECT-TYPE
    SYNTAX      Unsigned32 (0..255)
    MAX-ACCESS  read-only
    STATUS      current
    DESCRIPTION
            "IP protocol number in traffic descriptor. A value
            of '0' represents a 'don't care' and the CP wants to set up
            QoS for traffic streams irrespective of the IpProtocol."
    ::= { ocHnQosTrafficDescEntry 9 }

ocHnQosTrafficV3TrafficIdSourceUuid OBJECT-TYPE
    SYNTAX      OCTET STRING
    MAX-ACCESS  read-only
    STATUS      current
    DESCRIPTION
            "Contains the UDN of the UPnP Device at the source. The
            UUID consists of the UDN of the device, including the
            prefix 'uuid:'."
    ::= { ocHnQosTrafficDescEntry 10 }

ocHnQosTrafficV3TrafficIdDestinationUuid OBJECT-TYPE
    SYNTAX      OCTET STRING
    MAX-ACCESS  read-only
    STATUS      current
    DESCRIPTION
            "Contains the UDN of the UPnP Device at the destination.
            The UUID consists of the UDN of the device, including 
            the prefix 'uuid:'."
    ::= { ocHnQosTrafficDescEntry 11 }

ocHnQosTrafficMediaServerConnectionId OBJECT-TYPE
    SYNTAX      Integer32 (-1..65534)
    MAX-ACCESS  read-only
    STATUS      current
    DESCRIPTION
            "Identifies the traffic stream established by 
            the UPnP-AV Control Point at the DMS for which 
            QoS is requested."
    ::= { ocHnQosTrafficDescEntry 12 }

ocHnQosTrafficMediaRendererConnectionId OBJECT-TYPE
    SYNTAX      Integer32 (-1..65534) 
    MAX-ACCESS  read-only
    STATUS      current
    DESCRIPTION
            "Identifies the traffic stream established by the 
            UPnP-AV Control Point at the DMR for which 
            QoS is requested."
    ::= { ocHnQosTrafficDescEntry 13 }

ocHnQosTrafficLeaseTime OBJECT-TYPE
    SYNTAX      Unsigned32 
    UNITS       "seconds" 
    MAX-ACCESS  read-only
    STATUS      current
    DESCRIPTION
            "This object contains the lease time associated 
            with a particular traffic stream. When not specified 
            (which MUST only occur for prioritized streams), it
            indicates an indefinite lease, i.e., the 
            TrafficDescriptor will remain active until it is 
            explicitly removed or the QosDevice is rebooted. The value
            reported in this object represents the remaining 
            lease time. A NULL must be returned if this object
            is not populated."
    ::= { ocHnQosTrafficDescEntry 14 }

ocHnQosTrafficCritical OBJECT-TYPE
    SYNTAX      TruthValue 
    MAX-ACCESS  read-only
    STATUS      current
    DESCRIPTION
            "The value expresses the control point's belief on whether
            this traffic stream is critical. Streams for entertainment
            are not critical traffic streams. Examples of critical 
            traffic streams are emergency alerts, emergency calls, etc.
            A NULL must be returned if this object is not populated."
    ::= { ocHnQosTrafficDescEntry 15 }

ocHnQosTrafficUserName OBJECT-TYPE
    SYNTAX      SnmpAdminString (SIZE (0..64))
    MAX-ACCESS  read-only
    STATUS      current
    DESCRIPTION
            "Contains a string associated with the user who requested 
            a particular traffic stream. This field identifies the name
            of the user initiating the UPnP-QoS Action."
    ::= { ocHnQosTrafficDescEntry 16 }

ocHnQosTrafficVendorApplicationName OBJECT-TYPE
    SYNTAX      OCTET STRING
    MAX-ACCESS  read-only
    STATUS      current
    DESCRIPTION
            "The value contains a single URI string associated with an
            application. This field identifies the name of the
            application initiating the UPnP-QoS Action. For
            applications specified by vendors, the value of this
            field MUST begin with 'urn:1', followed by an ICANN domain
            name owned by the vendor, followed by 
            ':application:', followed by an application name.
            A NULL must be returned if this object is not populated."
    ::= { ocHnQosTrafficDescEntry 17 }

ocHnQosTrafficPortName OBJECT-TYPE
    SYNTAX      OCTET STRING 
    MAX-ACCESS  read-only
    STATUS      current
    DESCRIPTION
            "The value contains a single URI string associated
            with the fixed port used by an application for its protocol
            set-up. This field, if present, shall identify the port
            number used by the application. The value of this field
            MUST begin with 'urn:', followed by an ICANN domain name
            owned by the vendor, followed by ':port:', followed by the
            port name. A NULL must be returned 
            if this object is not populated."
    ::= { ocHnQosTrafficDescEntry 18 }

ocHnQosTrafficServiceProviderServiceName OBJECT-TYPE
    SYNTAX      OCTET STRING 
    MAX-ACCESS  read-only
    STATUS      current
    DESCRIPTION
            "The value contains a single URI string associated
            with a service offered by a service provider. This field
            identifies the name of the service offered by a service
            provider. For services provided by service providers, the
            value of this field MUST begin with 'urn:', followed by an
            ICANN domain name owned by a service provider, followed
            by ':service:', followed by a service name.
            A NULL must be returned if this object is not populated."
    ::= { ocHnQosTrafficDescEntry 19 }

ocHnQosTrafficCpName OBJECT-TYPE
    SYNTAX      SnmpAdminString 
    MAX-ACCESS  read-only
    STATUS      current
    DESCRIPTION
            "The value is a string associated with the Control Point
            Requesting QoS for the traffic stream. This field
            identifies the name of the Control Point initiating the
            UPnP-QoS Action. A NULL must be returned if this object
            is not populated."
    ::= { ocHnQosTrafficDescEntry 20 }

--
-- TSpec table. Populated only when triggered 
-- by setting the ocHnQosStreamsInfoCollectionTrigger to true(1).
--

ocHnQosTspecTable OBJECT-TYPE
    SYNTAX      SEQUENCE OF OcHnQosTspecEntry
    MAX-ACCESS  not-accessible
    STATUS      current
    DESCRIPTION
            "This table contains the Traffic Specification (TSPEC) 
           list. Each row represents a set of parameters that define 
           the characteristics of the traffic stream. The TSPEC defines
           the resource requirements for carrying the traffic stream."
    ::= { ocHnQosTrafficInfo 3 }

ocHnQosTspecEntry OBJECT-TYPE
    SYNTAX      OcHnQosTspecEntry
    MAX-ACCESS  not-accessible
    STATUS      current
    DESCRIPTION
            "Each entry represents one stream traffic descriptor."
    INDEX { ocHnQosTspecTableIndex, ocHnQosTrafficHandle }
    ::= { ocHnQosTspecTable 1 }

OcHnQosTspecEntry ::=
    SEQUENCE {
        ocHnQosTspecTableIndex
            Unsigned32,
        ocHnQosTspec
            Unsigned32,
        ocHnQosActiveTspec
            TruthValue,
        ocHnQosTspecTrafficClass
            INTEGER,
        ocHnQosTspecReqQosType
            INTEGER,
        ocHnQosTspecDataRate
            Unsigned32,
        ocHnQosTspecPeakDataRate
            Unsigned32, 
        ocHnQosTspecMaxBurstSize
            Unsigned32, 
        ocHnQosTspecMaxPacketSize
            Unsigned32,
        ocHnQosTspecE2EMaxDelayHigh
            Unsigned32,
        ocHnQosTspecE2EMaxJitter
            Unsigned32
        } 

ocHnQosTspecTableIndex OBJECT-TYPE
    SYNTAX      Unsigned32 (1..4294967295)
    MAX-ACCESS  not-accessible
    STATUS      current
    DESCRIPTION
            "Table Index. The unique TrafficHandle serves as a
            Secondary index into this table. This allows the
            Network manager to view all the TSPECs associated with 
            a given TrafficHandle."
    ::= { ocHnQosTspecEntry 1 }

ocHnQosTspec OBJECT-TYPE
    SYNTAX      Unsigned32
    MAX-ACCESS  read-only
    STATUS      current
    DESCRIPTION
            "The value of Tspec reflects the order of preference. 
             TspecIndex values need not be
             consecutive numbers."
    ::= { ocHnQosTspecEntry 2 }

ocHnQosActiveTspec OBJECT-TYPE
    SYNTAX      TruthValue
    MAX-ACCESS  read-only
    STATUS      current
    DESCRIPTION
            "Only one Tspec can be active for a specific TrafficHandle.
            'True' signifies the entry is active. 'False' implies the
             Tspec can potentially be utilized."
    ::= { ocHnQosTspecEntry 3 }

ocHnQosTspecTrafficClass OBJECT-TYPE
    SYNTAX      INTEGER {
                        other(1),
                        networkControl(2),
                        streamingControl(3),
                        voice(4),
                        av(5),
                        data(6),
                        audio(7),
                        image(8),
                        background(9),
                        gaming(10)
                        }
    MAX-ACCESS  read-only
    STATUS      current
    DESCRIPTION
            "Contains the traffic class associated with 
            the traffic stream."
    ::= { ocHnQosTspecEntry 4 }

ocHnQosTspecReqQosType OBJECT-TYPE
    SYNTAX      INTEGER {
                        prioritized(1),
                        hybrid(2),
                        parameterized(3)
                        }
    MAX-ACCESS  read-only
    STATUS      current
    DESCRIPTION
            "Specifies the type of Quality of Service 
            that is requested with this traffic descriptor."
    ::= { ocHnQosTspecEntry 5 }

ocHnQosTspecDataRate OBJECT-TYPE
    SYNTAX      Unsigned32
    UNITS       "octets/sec"
    MAX-ACCESS  read-only
    STATUS      current
    DESCRIPTION
            "This value intends to characterize the
            long term data rate."
    ::= { ocHnQosTspecEntry 6 }

ocHnQosTspecPeakDataRate OBJECT-TYPE
    SYNTAX      Unsigned32
    UNITS       "octets/sec"
    MAX-ACCESS  read-only
    STATUS      current
    DESCRIPTION
            "Defines an upper bound on the data rate at which this 
            traffic stream needs to be served in order to serve the
            traffic stream within time. If not provided, the default
            is the ocHnQosTrafficTspecDataRate."
    ::= { ocHnQosTspecEntry 7 }

ocHnQosTspecMaxBurstSize OBJECT-TYPE
    SYNTAX      Unsigned32
    UNITS       "octets/sec"
    MAX-ACCESS  read-only
    STATUS      current
    DESCRIPTION
            "Maximum burst size. A value of zero indicates
            a constant bit rate with no bursts."
    ::= { ocHnQosTspecEntry 8 }

ocHnQosTspecMaxPacketSize OBJECT-TYPE
    SYNTAX      Unsigned32
    UNITS       "bytes"
    MAX-ACCESS  read-only
    STATUS      current
    DESCRIPTION
            "Conveys the information about packetization of traffic 
            streams by an application. The packet size includes the 
            application data and an approximation of the overhead
            of all protocol headers at and above the IP layer.
            The default is 1500 if not specified."
    ::= { ocHnQosTspecEntry 9 }

ocHnQosTspecE2EMaxDelayHigh OBJECT-TYPE
    SYNTAX      Unsigned32 
    UNITS       "microseconds" 
    MAX-ACCESS  read-only
    STATUS      current
    DESCRIPTION
            "Specifies the desired upper bound of the End-to-End 
            Delay of individual packets belonging to the traffic
            stream."
    ::= { ocHnQosTspecEntry 10 }

ocHnQosTspecE2EMaxJitter OBJECT-TYPE
    SYNTAX      Unsigned32 
    UNITS       "microseconds" 
    MAX-ACCESS  read-only
    STATUS      current
    DESCRIPTION
            "Specifies an UPPER bound to the End-to-End Jitter."
    ::= { ocHnQosTspecEntry 11 }

--
-- Policy table - One row is created
-- for each TLV 56 (RSD Configuration TLV) 
--

ocHnQosPolicyTable OBJECT-TYPE
    SYNTAX      SEQUENCE OF OcHnQosPolicyEntry
    MAX-ACCESS  not-accessible
    STATUS      current
    DESCRIPTION
            "This table contains the operator and user-created
            policies for the management of QoS for applications."
    ::= { ocHnQos 2 }

ocHnQosPolicyEntry OBJECT-TYPE
    SYNTAX      OcHnQosPolicyEntry
    MAX-ACCESS  not-accessible
    STATUS      current
    DESCRIPTION
            "Each entry represents one QoS policy."
    INDEX { ocHnQosPolicyRuleIdentifier }
    ::= { ocHnQosPolicyTable 1 }

OcHnQosPolicyEntry ::=
    SEQUENCE {
        ocHnQosPolicyRuleIdentifier
            Unsigned32,
        ocHnQosPolicyRowStatus
            RowStatus,
        ocHnQosPolicyIpAddressType
            InetAddressType,
        ocHnQosPolicySourceAddressUpLimit
            InetAddress,
        ocHnQosPolicySourceAddressLowLimit
            InetAddress,
        ocHnQosPolicySourcePortUpLimit
            InetPortNumber,
        ocHnQosPolicySourcePortLowLimit
            InetPortNumber,
        ocHnQosPolicyDestinationAddressUpLimit
            InetAddress,
         ocHnQosPolicyDestinationAddressLowLimit
            InetAddress,
         ocHnQosPolicyDestinationPortUpLimit
            InetPortNumber,
         ocHnQosPolicyDestinationPortLowLimit
            InetPortNumber,
         ocHnQosPolicyIpProtocolUpLimit
            Unsigned32,
         ocHnQosPolicyIpProtocolLowLimit
            Unsigned32,
         ocHnQosPolicyTrafficClass
            INTEGER,
         ocHnQosPolicyPeakDataRateUpLimit
            Unsigned32, 
         ocHnQosPolicyPeakDataRateLowLimit
            Unsigned32, 
         ocHnQosPolicyMeanDataRateUpLimit
            Unsigned32, 
         ocHnQosPolicyMeanDataRateLowLimit
            Unsigned32, 
         ocHnQosPolicyMaxBurstSizeUpLimit
            Unsigned32, 
         ocHnQosPolicyMaxBurstSizeLowLimit
            Unsigned32, 
         ocHnQosPolicyE2EMaxDelayHighLimit
            Unsigned32, 
         ocHnQosPolicyE2EMaxDelayLowLimit
            Unsigned32, 
         ocHnQosPolicyBoundaryAddressType
            InetAddressType, 
         ocHnQosPolicyBoundarySourceAddressUpLimit
            InetAddress,
         ocHnQosPolicyBoundarySourceAddressLowLimit
            InetAddress,
         ocHnQosPolicyBoundaryDestinationAddressUpLimit
            InetAddress,
         ocHnQosPolicyBoundaryDestinationAddressLowLimit
            InetAddress,
         ocHnQosPolicyUserName
            SnmpAdminString,
         ocHnQosPolicyVendorApplicationName
            SnmpAdminString,
         ocHnQosPolicyPortName
            SnmpAdminString,
         ocHnQosPolicyServiceProviderServiceName
            SnmpAdminString,
         ocHnQosPolicyCriticalFlag
            TruthValue,
         ocHnQosPolicyRequestedQosType
            INTEGER,
         ocHnQosPolicyStartTime
            Unsigned32,
         ocHnQosPolicyEndTime
            Unsigned32,
         ocHnQosPolicyTrafficLeaseTimeUpValue
            Unsigned32, 
         ocHnQosPolicyTrafficLeaseTimeLowValue
            Unsigned32,
         ocHnQosPolicyRuleType
            INTEGER, 
         ocHnQosPolicyRulePriority
            Unsigned32, 
         ocHnQosPolicyTrafficImportanceNumber
            Unsigned32, 
         ocHnQosPolicyUserImportanceNumber
            Unsigned32
         }

ocHnQosPolicyRuleIdentifier OBJECT-TYPE
    SYNTAX      Unsigned32 (0..65535)
    MAX-ACCESS  not-accessible
    STATUS      current
    DESCRIPTION
            "Unique identifier for each policy."
    ::= { ocHnQosPolicyEntry 1 }

ocHnQosPolicyRowStatus OBJECT-TYPE
    SYNTAX      RowStatus
    MAX-ACCESS  read-create
    STATUS      current
    DESCRIPTION
            "Controls and reflects the status of rows in this
            Table (see RowStatus textual convention). There 
            is no restriction on changing any of the associated
            columns for this row while this object is set
            to active (i.e., columnar objects can be modified
            when the row is active)."
    ::= { ocHnQosPolicyEntry 2}

ocHnQosPolicyIpAddressType OBJECT-TYPE
    SYNTAX      InetAddressType
    MAX-ACCESS  read-create
    STATUS      current
    DESCRIPTION
            "IPv4 or IPv6. Textual convention will 
            report IPv4(1) or IPv6(2) This Type applies
            to all IP addresses in this row."
    ::= { ocHnQosPolicyEntry 3 }

ocHnQosPolicySourceAddressUpLimit OBJECT-TYPE
    SYNTAX      InetAddress
    MAX-ACCESS  read-create
    STATUS      current
    DESCRIPTION
            "The upper limit for source of traffic stream(s) 
            for which a QoS Policy rule is applied. Default 
            value for this field is of all ones 
            (255.255.255.255 for IPv4 and 
            ffff: ffff: ffff: ffff: ffff: ffff: ffff: ffff: for IPv6),
            and it represents that no upper limit is specified for 
            the Source IP address."
    ::= { ocHnQosPolicyEntry 4 }

ocHnQosPolicySourceAddressLowLimit OBJECT-TYPE
    SYNTAX      InetAddress
    MAX-ACCESS  read-create
    STATUS      current
    DESCRIPTION
            "Identifies the lower limit for source of traffic stream(s)
            for which a QoS Policy rule is applied. A default value for
            this field is all zeros (0.0.0.0 for IPv4 and :: for IPv6),
            and it represents that no lower limit is specified for the
            Source IP Address."
    ::= { ocHnQosPolicyEntry 5 }

ocHnQosPolicySourcePortUpLimit OBJECT-TYPE
    SYNTAX      InetPortNumber
    MAX-ACCESS  read-create
    STATUS      current
    DESCRIPTION
            "Specifies the upper limit for port of source of traffic 
            stream(s) for which a QoS Policy rule is applied. A default
            value for this field is 65535, and it represents that no 
            upper limit is specified for the Source Port."
    ::= { ocHnQosPolicyEntry 6 } 

ocHnQosPolicySourcePortLowLimit OBJECT-TYPE
    SYNTAX      InetPortNumber
    MAX-ACCESS  read-create
    STATUS      current
    DESCRIPTION
            "Specifies the lower limit for port of source of traffic 
            stream(s) for which a QoS Policy rule is applied. A default
            value for this field is 0, and it represents that no 
            lower limit is specified for the Source Port."
    ::= { ocHnQosPolicyEntry 7 } 

ocHnQosPolicyDestinationAddressUpLimit  OBJECT-TYPE
    SYNTAX      InetAddress
    MAX-ACCESS  read-create
    STATUS      current
    DESCRIPTION
            "The upper limit for destination of traffic stream(s) 
            for which a QoS Policy rule is applied. Default 
            value for this field is of all ones 
            (255.255.255.255 for IPv4 and 
            ffff: ffff: ffff: ffff: ffff: ffff: ffff: ffff: for IPv6),
            and it represents that no upper limit is specified for 
            the destination IP address."
    ::= { ocHnQosPolicyEntry 8 }

ocHnQosPolicyDestinationAddressLowLimit  OBJECT-TYPE
    SYNTAX      InetAddress
    MAX-ACCESS  read-create
    STATUS      current
    DESCRIPTION
            "Identifies the lower limit for destination of traffic 
            stream(s) for which a QoS Policy rule is applied. A default
            value for this field is all zeros (0.0.0.0 for IPv4
            and :: for IPv6), and it represents that no lower limit
            is specified for the destination IP Address."
    ::= { ocHnQosPolicyEntry 9 }

ocHnQosPolicyDestinationPortUpLimit OBJECT-TYPE
    SYNTAX      InetPortNumber 
    MAX-ACCESS  read-create
    STATUS      current
    DESCRIPTION
            "Specifies the upper limit for port of destination of
            traffic stream(s) for which a QoS Policy rule is applied.
            A default value for this field is 65535, and it represents
            that no upper limit is specified for the destination Port."
    ::= { ocHnQosPolicyEntry 10 } 

ocHnQosPolicyDestinationPortLowLimit OBJECT-TYPE
    SYNTAX      InetPortNumber
    MAX-ACCESS  read-create
    STATUS      current
    DESCRIPTION
            "Specifies the lower limit for port of destination of 
            traffic stream(s) for which a QoS Policy rule is applied.
            A default value for this field is 0, and it represents that
            no lower limit is specified for the destination Port."
    ::= { ocHnQosPolicyEntry 11 }

ocHnQosPolicyIpProtocolUpLimit OBJECT-TYPE
    SYNTAX      Unsigned32 (0..255) 
    MAX-ACCESS  read-create
    STATUS      current
    DESCRIPTION
            "Specifies an IANA-assigned upper limit for IP protocol 
            number of traffic stream(s) for which a QoS Policy rule is
            applied. A default value for this field is 255, and it
            represents that no upper limit is specified for the
            IP Protocol."
    ::= { ocHnQosPolicyEntry 12 }

ocHnQosPolicyIpProtocolLowLimit OBJECT-TYPE
    SYNTAX      Unsigned32 (0..255) 
    MAX-ACCESS  read-create
    STATUS      current
    DESCRIPTION
            "Specifies an IANA-assigned lower limit for IP protocol
            number of traffic stream(s) for which a QoS Policy rule is
            applied. A default value for this field is 0, and it
            represents that no lower limit is specified for the
            IP Protocol."
    ::= { ocHnQosPolicyEntry 13 }

ocHnQosPolicyTrafficClass OBJECT-TYPE
    SYNTAX      INTEGER {
                        networkControl(0),
                        streamingControl(1),
                        voice(2),
                        av(3),
                        data(4),
                        audio(5),
                        image(6),
                        gaming(7),
                        other(8),
                        background(9)
                        } 
    MAX-ACCESS  read-create
    STATUS      current
    DESCRIPTION
            "Specifies the traffic class associated with traffic
            stream(s) for which a QoS Policy rule is applied."
    ::= { ocHnQosPolicyEntry 14 }

ocHnQosPolicyPeakDataRateUpLimit OBJECT-TYPE
    SYNTAX      Unsigned32 
    UNITS       "octets/sec" 
    MAX-ACCESS  read-create
    STATUS      current
    DESCRIPTION
            "Specifies the upper limit for PeakDataRate of traffic
            stream(s) for which a QoS Policy rule is applied."
    ::= { ocHnQosPolicyEntry 15 }

ocHnQosPolicyPeakDataRateLowLimit OBJECT-TYPE
    SYNTAX      Unsigned32 
    UNITS       "octets/sec" 
    MAX-ACCESS  read-create
    STATUS      current
    DESCRIPTION
            "Specifies the lower limit for PeakDataRate of traffic
            stream(s) for which a QoS Policy rule is applied."
    ::= { ocHnQosPolicyEntry 16 }

ocHnQosPolicyMeanDataRateUpLimit OBJECT-TYPE
    SYNTAX      Unsigned32 
    UNITS       "octets/sec" 
    MAX-ACCESS  read-create
    STATUS      current
    DESCRIPTION
            "Specifies the upper limit for MeanDataRate of traffic
            stream(s) for which a QoS Policy rule is applied."
    ::= { ocHnQosPolicyEntry 17 }

ocHnQosPolicyMeanDataRateLowLimit OBJECT-TYPE
    SYNTAX      Unsigned32 
    UNITS       "octets/sec" 
    MAX-ACCESS  read-create
    STATUS      current
    DESCRIPTION
            "Specifies the lower limit for MeanDataRate of traffic
            stream(s) for which a QoS Policy rule is applied."
    ::= { ocHnQosPolicyEntry 18 }

ocHnQosPolicyMaxBurstSizeUpLimit OBJECT-TYPE
    SYNTAX      Unsigned32 
    UNITS       "octets/sec" 
    MAX-ACCESS  read-create
    STATUS      current
    DESCRIPTION
            "Specifies the upper limit for MaxBurstSize of traffic
            stream(s) for which a QoS Policy rule is applied."
    ::= { ocHnQosPolicyEntry 19 }

ocHnQosPolicyMaxBurstSizeLowLimit OBJECT-TYPE
    SYNTAX      Unsigned32 
    UNITS       "octets/sec" 
    MAX-ACCESS  read-create
    STATUS      current
    DESCRIPTION
            "Specifies the lower limit for MaxBurstSize of traffic
            stream(s) for which a QoS Policy rule is applied."
    ::= { ocHnQosPolicyEntry 20 }

ocHnQosPolicyE2EMaxDelayHighLimit OBJECT-TYPE
    SYNTAX      Unsigned32 
    UNITS       "microseconds" 
    MAX-ACCESS  read-create
    STATUS      current
    DESCRIPTION
            "Specifies the upper limit of E2EMaxDelayHigh 
            (End-to-end delay) parameter for traffic stream(s) for
             which a QoS Policy rule is applied."
    ::= { ocHnQosPolicyEntry 21 }

ocHnQosPolicyE2EMaxDelayLowLimit
    OBJECT-TYPE
    SYNTAX      Unsigned32 
    UNITS       "microseconds" 
    MAX-ACCESS  read-create
    STATUS      current
    DESCRIPTION
            "Specifies the lower limit of E2EMaxDelayLow 
            (End-to-end delay) parameter for
            traffic stream(s) for which a QoS Policy rule is applied."
    ::= { ocHnQosPolicyEntry 22 }

ocHnQosPolicyBoundaryAddressType OBJECT-TYPE
    SYNTAX      InetAddressType
    MAX-ACCESS  read-create
    STATUS      current
    DESCRIPTION
            "IPv4 or IPv6. Textual convention will 
             report IPv4(1) or IPv6(2). This Type applies
             to all IP addresses in this row."
    ::= { ocHnQosPolicyEntry 23 }

ocHnQosPolicyBoundarySourceAddressUpLimit OBJECT-TYPE
    SYNTAX      InetAddress
    MAX-ACCESS  read-create
    STATUS      current
    DESCRIPTION
            "The upper limit for source of traffic stream(s) 
            for which a QoS Policy rule is applied. Default 
            value for this field is of all ones 
            (255.255.255.255 for IPv4 and 
            ffff: ffff: ffff: ffff: ffff: ffff: ffff: ffff: for IPv6),
            and it represents that no upper limit is specified for 
            the Source IP address. Address format must be consistent
            with ocHnQosPolicyBoundaryAddressType."
    ::= { ocHnQosPolicyEntry 24 }

ocHnQosPolicyBoundarySourceAddressLowLimit OBJECT-TYPE
    SYNTAX      InetAddress
    MAX-ACCESS  read-create
    STATUS      current
    DESCRIPTION
            "The lower limit for source of traffic stream(s) 
            for which a QoS Policy rule is applied. A default value for
            this field is all zeros (0.0.0.0 for IPv4 and :: for IPv6),
            which represents that no lower limit is specified. Address
            format must be consistent with
            ocHnQosPolicyBoundaryAddressType."
    ::= { ocHnQosPolicyEntry 25 }

ocHnQosPolicyBoundaryDestinationAddressUpLimit OBJECT-TYPE
    SYNTAX      InetAddress
    MAX-ACCESS  read-create
    STATUS      current
    DESCRIPTION
            "The upper limit for destination of traffic stream(s) 
            for which a QoS Policy rule is applied. Default 
            value for this field is of all ones 
            (255.255.255.255 for IPv4 and 
            ffff: ffff: ffff: ffff: ffff: ffff: ffff: ffff: for IPv6),
            and it represents that no upper limit is specified for 
            the Destination IP address. Address format must be
            consistent with ocHnQosPolicyBoundaryAddressType."
    ::= { ocHnQosPolicyEntry 26 }

ocHnQosPolicyBoundaryDestinationAddressLowLimit OBJECT-TYPE
    SYNTAX      InetAddress
    MAX-ACCESS  read-create
    STATUS      current
    DESCRIPTION
            "The lower limit for destination of traffic stream(s) 
            for which a QoS Policy rule is applied. A default value for
            this field is all zeros (0.0.0.0 for IPv4 and :: for IPv6),
            which represents that no lower limit is specified for the
            Destination IP address. Address format must be consistent
            with ocHnQosPolicyBoundaryAddressType."
    ::= { ocHnQosPolicyEntry 27 }

ocHnQosPolicyUserName OBJECT-TYPE
    SYNTAX      SnmpAdminString
    MAX-ACCESS  read-create
    STATUS      current
    DESCRIPTION
            "This field identifies the name of the user initiating the
            UPnP-QoS action. The field is <= 64 UTF-8 characters.
            At present, the semantics for this field are not defined.
            A null should be returned if no value exists."
    ::= { ocHnQosPolicyEntry 28 }

ocHnQosPolicyVendorApplicationName OBJECT-TYPE
    SYNTAX      SnmpAdminString
    MAX-ACCESS  read-create
    STATUS      current
    DESCRIPTION
            "This field identifies the name of the application
            initiating the UPnP-QoS Action. A NULL should be returned
            if no value exists."
    ::= { ocHnQosPolicyEntry 29 }

ocHnQosPolicyPortName OBJECT-TYPE
    SYNTAX      SnmpAdminString
    MAX-ACCESS  read-create
    STATUS      current
    DESCRIPTION
            "This value, if present, contains a single URI string
            associated with the fixed port used by an application
            for its protocol set-up. A NULL should be returned if
            no value exists."
    ::= { ocHnQosPolicyEntry 30 }

ocHnQosPolicyServiceProviderServiceName OBJECT-TYPE
    SYNTAX      SnmpAdminString
    MAX-ACCESS  read-create
    STATUS      current
    DESCRIPTION
            "This object contains a single URI string associated with
            the name of the service offered by a service provider.
            A NULL should be returned if no value exists."
    ::= { ocHnQosPolicyEntry 31 }

ocHnQosPolicyCriticalFlag OBJECT-TYPE
    SYNTAX      TruthValue
    MAX-ACCESS  read-create
    STATUS      current
    DESCRIPTION
            "Specifies the Critical Flag for traffic stream(s) for
            which a QoS Policy rule is applied. This flag can be set
            to get a higher UIN to protect a stream from preemption
            or to be able to always get admitted. Streams for
            entertainment are not critical traffic streams. This flag
            can be used for services like EAS messages, E-911 calls,
            voice calls, etc. The default value is False(2)."
    ::= { ocHnQosPolicyEntry 32 }

ocHnQosPolicyRequestedQosType OBJECT-TYPE
    SYNTAX      INTEGER {
                     fullyPrioritized(1),
                     hybrid(2),
                     fullyParameterized(3)
                     }
    MAX-ACCESS  read-create
    STATUS      current
    DESCRIPTION
            "Specifies the Requested QoS Type for traffic stream(s) for
            which a QoS Policy rule is applied. If supplied, it SHALL
            contain a non-negative integer value. It is used to
            indicate the type of Quality of Service that is requested
            for a traffic stream. The default value is 1."
    ::= { ocHnQosPolicyEntry 33 }

ocHnQosPolicyStartTime OBJECT-TYPE
    SYNTAX      Unsigned32 (0..604800)
    MAX-ACCESS  read-create
    STATUS      current
    DESCRIPTION
            "Specifies the starting Time Of Day (Day/Time)for a QoS
            Policy Rule. Time is specified in seconds and ranges 
            from 0 - 604800 (to cover 7 days of week). Time 0 is Sunday
            12 midnight. If not specified, this object returns a NULL."
    ::= { ocHnQosPolicyEntry 34 }

ocHnQosPolicyEndTime OBJECT-TYPE
    SYNTAX      Unsigned32 (0..604800)
    MAX-ACCESS  read-create
    STATUS      current
    DESCRIPTION
            "Specifies the ending Time Of Day (Day/Time)for a QoS
            Policy Rule. Time is specified in seconds and ranges
            from 0 - 604800 (to cover 7 days of week). Time 0 is
            Sunday 12 midnight. If not specified, this object
            returns a NULL."
    ::= { ocHnQosPolicyEntry 35 }

ocHnQosPolicyTrafficLeaseTimeUpValue OBJECT-TYPE
    SYNTAX      Unsigned32 (0..604800)
    MAX-ACCESS  read-create
    STATUS      current
    DESCRIPTION
            "Specifies the upper limit for lease time for reservation
            of QoS resources associated with traffic stream(s) for
            which a QoS Policy rule is applied. If not specified,
            this object returns a NULL."
    ::= { ocHnQosPolicyEntry 36 }

ocHnQosPolicyTrafficLeaseTimeLowValue OBJECT-TYPE
    SYNTAX      Unsigned32 (0..604800)
    MAX-ACCESS  read-create
    STATUS      current
    DESCRIPTION
            "Specifies the lower limit for lease time for reservation
            of QoS resources associated with traffic stream(s) for
            which a QoS Policy rule is applied. If not specified, this
            object returns a NULL."
    ::= { ocHnQosPolicyEntry 37 }

ocHnQosPolicyRuleType OBJECT-TYPE
    SYNTAX      INTEGER {
                     operatorOnly(0),
                     homeUser(1),
                     operatorForHomeUser(2),
                     other(3)
                     }
    MAX-ACCESS  read-create
    STATUS      current
    DESCRIPTION
            "Identifies the type of a QoS Policy rule based
            on who configures the rule and for what purpose."
    ::= { ocHnQosPolicyEntry 38 } 

ocHnQosPolicyRulePriority OBJECT-TYPE 
    SYNTAX      Unsigned32 (0..65535)
    MAX-ACCESS  read-create
    STATUS      current
    DESCRIPTION
            "Specifies the priority for a QoS Policy rule. QoS policy
            rules are processed according to their Rule Priority value,
            the highest to the lowest."
    ::= { ocHnQosPolicyEntry 39 }

ocHnQosPolicyTrafficImportanceNumber OBJECT-TYPE 
    SYNTAX      Unsigned32 (1..7)
    MAX-ACCESS  read-create
    STATUS      current
    DESCRIPTION
            "Specifies traffic priority to be utilized for tagging
            packets belonging to traffic stream(s) for which this
            QoS Policy Rule is applied."
    ::= { ocHnQosPolicyEntry 40 }

ocHnQosPolicyUserImportanceNumber OBJECT-TYPE 
    SYNTAX      Unsigned32 (0..255)
    MAX-ACCESS  read-create
    STATUS      current
    DESCRIPTION
            "Specifies the User Importance Number for traffic stream(s)
            for which this QoS Policy Rule is applied. It determines
            the stream importance from users' perspective. It is used
            for admission control and preemption purposes."
    ::= { ocHnQosPolicyEntry 41 }

--
-- QoS Statistics for RSD Technologies only 
--

ocHnQosROStatsTable OBJECT-TYPE
    SYNTAX      SEQUENCE OF OcHnQosROStatsEntry
    MAX-ACCESS  not-accessible
    STATUS      current
    DESCRIPTION
            "This table reports the common values carried in each 
            Rotameter Observation collected. It also provides the
            anchor index for the related tables (e.g., parameterized
            and prioritized stream statistics)."
    ::= { ocHnQos 3 }

ocHnQosROStatsEntry OBJECT-TYPE
    SYNTAX      OcHnQosROStatsEntry
    MAX-ACCESS  not-accessible
    STATUS      current
    DESCRIPTION
            "One entry for each observation."
    INDEX { ocHnQosROStatsIndex }
    ::= { ocHnQosROStatsTable 1 }

OcHnQosROStatsEntry  ::=
    SEQUENCE {
        ocHnQosROStatsIndex
            Unsigned32,
        ocHnQosROStatsIdentifier
            Unsigned32, 
        ocHnQosROStatsMacAddress
            MacAddress,
        ocHnQosROStatsObservationMacAddress
            MacAddress,
        ocHnQosROStatsQosSegmentId
            OCTET STRING,
        ocHnQosROStatsTotalTrafficBytes
            Counter32,
        ocHnQosROStatsTotalParameterizedBytes
            Counter32,
        ocHnQosROStatsTotalParameterizedPackets
            Counter32,
        ocHnQosROStatsTotalParameterizedPacketsDropped
            Counter32,
        ocHnQosROStatsReportingDateAndTime
            SnmpAdminString,
        ocHnQosROStatsObservationPeriod
            Unsigned32,
        ocHnQosROStatsMonitorResolutionPeriod
            Unsigned32
        }

ocHnQosROStatsIndex OBJECT-TYPE
    SYNTAX      Unsigned32 (1..4294967295)
    MAX-ACCESS  not-accessible
    STATUS      current
    DESCRIPTION
            "Table Index. This will serve as an external index 
            to related statistics tables."
    ::= { ocHnQosROStatsEntry 1 }

ocHnQosROStatsIdentifier OBJECT-TYPE
    SYNTAX      Unsigned32 
    MAX-ACCESS  read-only
    STATUS      current
    DESCRIPTION
            "Unique identifier for each observation on the device."
    ::= { ocHnQosROStatsEntry 2 }

ocHnQosROStatsMacAddress OBJECT-TYPE
    SYNTAX      MacAddress
    MAX-ACCESS  read-only
    STATUS      current
    DESCRIPTION
            "MAC Address of the interface on a device that is
            collecting these statistics."
    ::= { ocHnQosROStatsEntry 3 }

ocHnQosROStatsObservationMacAddress OBJECT-TYPE
    SYNTAX      MacAddress
    MAX-ACCESS  read-only
    STATUS      current
    DESCRIPTION
            "This is the MAC address of an interface on a QosDevice
            Service at which the Rotameter observation information
            is provided. If it is the same address as
            ocHnQosROStatsMacAddress parameter, then the Rotameter
            observation is for all traffic to/from the interface
            identified by the ocHnQosROStatsMacAddress field on this
            device. If the address is different from the
            OcHnQosROStatsMacAddress parameter, then the Rotameter
            observation is for all traffic between the interface
            identified by the ocHnQosROStatsObservationMacAddress field
            on another device (which may not be a QosDevice Service)
            and the interface identified by the
            ocHnQosROStatsMacAddress parameter on this device.
            If the address is all zeros, then the Rotameter observation
            is for the entire QosSegment of the shared media technology
            identified by the QosSegmentId. For example, this parameter
            will be set to all zeros by a device that is a Layer2
            scheduler for a QosSegment when reporting statistics
            information for the entire QosSegment."
    ::= { ocHnQosROStatsEntry 4 }

ocHnQosROStatsQosSegmentId OBJECT-TYPE
    SYNTAX      OCTET STRING
    MAX-ACCESS  read-create
    STATUS      current
    DESCRIPTION
            "This uniquely identifies a network segment of a shared
            Media technology. This parameter needs
            to be configured to obtain traffic statistics for a 
            specific QosSegment and for a specific traffic stream 
            identified by a combination of Layer2StreamId and a 
            QosSegmentId. The default value of 0 indicates no 
            QosSegment is specified."
    ::= { ocHnQosROStatsEntry 5 }

ocHnQosROStatsTotalTrafficBytes OBJECT-TYPE
    SYNTAX      Counter32 
    MAX-ACCESS  read-only
    STATUS      current
    DESCRIPTION
            "Total number of bytes of all streams (best effort, 
            prioritized, and parameterized) measured in the 
            observation period. A null value should be reported if
            no rotameter information is available."
    ::= { ocHnQosROStatsEntry 6 }

ocHnQosROStatsTotalParameterizedBytes OBJECT-TYPE
    SYNTAX      Counter32 
    MAX-ACCESS  read-only
    STATUS      current
    DESCRIPTION
            "Total number of bytes for all parameterized streams 
            in the observation period. A null value should be 
            reported if no rotameter information is available." 
    ::= { ocHnQosROStatsEntry 7 }

ocHnQosROStatsTotalParameterizedPackets OBJECT-TYPE
    SYNTAX      Counter32 
    MAX-ACCESS  read-only
    STATUS      current
    DESCRIPTION
            "Total number of packets of all parameterized 
            streams measured in the observation period. A null value
            should be reported if no rotameter information is
            available." 
    ::= { ocHnQosROStatsEntry 8 }

ocHnQosROStatsTotalParameterizedPacketsDropped OBJECT-TYPE
    SYNTAX      Counter32 
    MAX-ACCESS  read-only
    STATUS      current
    DESCRIPTION
            "Total number of packets dropped at layer-2 for all the
            parameterized streams in the observation period. A null
            value should be reported if no rotameter information is
            available."
    ::= { ocHnQosROStatsEntry 9 }

ocHnQosROStatsReportingDateAndTime OBJECT-TYPE
    SYNTAX      SnmpAdminString 
    MAX-ACCESS  read-only
    STATUS      current
    DESCRIPTION
            "Time of Completion of Observation Period. This is wall 
            clock time formatted per [RFC3339], which can potentially
            be non-synchronized with other devices on the network."
    ::= { ocHnQosROStatsEntry 10 }

ocHnQosROStatsObservationPeriod OBJECT-TYPE
    SYNTAX      Unsigned32 
    MAX-ACCESS  read-only
    STATUS      current
    DESCRIPTION
            "This integer field specifies the duration in seconds over
            which the RotameterObservation is performed."
    ::= { ocHnQosROStatsEntry 11 }

ocHnQosROStatsMonitorResolutionPeriod OBJECT-TYPE 
    SYNTAX      Unsigned32 
    MAX-ACCESS  read-only
    STATUS      current
    DESCRIPTION
            "This integer field specifies, in seconds, how often a 
            Rotameter observation is initiated."
    ::= { ocHnQosROStatsEntry 12 }

ocHnQosStreamStatisticsTable OBJECT-TYPE
    SYNTAX      SEQUENCE OF OcHnQosStreamStatisticsEntry
    MAX-ACCESS  not-accessible
    STATUS      current
    DESCRIPTION
            "This table reports stream-specific statistics
            collected as a result of the current rotameter observation.
            Null values must be returned if no observations have been 
            collected."
    ::= { ocHnQos 4 }

ocHnQosStreamStatisticsEntry OBJECT-TYPE
    SYNTAX      OcHnQosStreamStatisticsEntry
    MAX-ACCESS  not-accessible
    STATUS      current
    DESCRIPTION
            "One entry report of counter values for 
            each unique streamId."
    INDEX { ocHnQosROStatsIndex }
    ::= { ocHnQosStreamStatisticsTable 1 }

OcHnQosStreamStatisticsEntry ::=
    SEQUENCE {
        ocHnQosStreamStatisticsTrafficHandle
            OCTET STRING,
        ocHnQosStreamStatisticsLayer2StreamId
            OCTET STRING,
        ocHnQosStreamStatisticsPktsTransmitted
            Counter32,
        ocHnQosStreamStatisticsPktsReceived
            Counter32,
        ocHnQosStreamStatisticsErrorPktsDropped
            Counter32,
        ocHnQosStreamStatisticsBytesTransmitted
            Counter32,
        ocHnQosStreamStatisticsBytesReceived
            Counter32,
        ocHnQosStreamStatisticsPeakDataRateViolations
            TruthValue
        }

ocHnQosStreamStatisticsTrafficHandle OBJECT-TYPE
    SYNTAX      OCTET STRING 
    MAX-ACCESS  read-only
    STATUS      current
    DESCRIPTION
            "Identifies a unique UPnP QoS traffic stream over the home
            network."
    ::= { ocHnQosStreamStatisticsEntry 1 }

ocHnQosStreamStatisticsLayer2StreamId OBJECT-TYPE
    SYNTAX      OCTET STRING (SIZE (64) )
    MAX-ACCESS  read-only
    STATUS      current
    DESCRIPTION
            "Identifies a unique traffic stream over an RSD Technology
            Qos Segment identified by a QosSegmentId."
    ::= { ocHnQosStreamStatisticsEntry 2 }

ocHnQosStreamStatisticsPktsTransmitted OBJECT-TYPE
    SYNTAX      Counter32
    MAX-ACCESS  read-only
    STATUS      current
    DESCRIPTION
            "This parameter reports total number of packets
            transmitted of a parameterized traffic stream
            specified in the current rotameter observation."
    ::= { ocHnQosStreamStatisticsEntry 3 }

ocHnQosStreamStatisticsPktsReceived OBJECT-TYPE
    SYNTAX      Counter32
    MAX-ACCESS  read-only
    STATUS      current
    DESCRIPTION
            "This parameter reports total number of packets
            received for a parameterized traffic stream specified
            in the current rotameter observation."
    ::= { ocHnQosStreamStatisticsEntry 4 }

ocHnQosStreamStatisticsErrorPktsDropped OBJECT-TYPE
    SYNTAX      Counter32
    MAX-ACCESS  read-only
    STATUS      current
    DESCRIPTION
            "This parameter reports total number of dropped packets
            at layer-2 of a parameterized traffic stream specified in
            the current rotameter observation."
    ::= { ocHnQosStreamStatisticsEntry 5 }

ocHnQosStreamStatisticsBytesTransmitted OBJECT-TYPE
    SYNTAX      Counter32
    MAX-ACCESS  read-only
    STATUS      current
    DESCRIPTION
            "This parameter reports total number of bytes transmitted of
            a parameterized traffic stream specified in 
            the current rotameter observation."
    ::= { ocHnQosStreamStatisticsEntry 6 }

ocHnQosStreamStatisticsBytesReceived OBJECT-TYPE
    SYNTAX      Counter32
    MAX-ACCESS  read-only
    STATUS      current
    DESCRIPTION
            "This parameter reports total number of bytes
            received of the parameterized traffic stream
            specified in the current rotameter observation."
    ::= { ocHnQosStreamStatisticsEntry 7 }

ocHnQosStreamStatisticsPeakDataRateViolations OBJECT-TYPE
    SYNTAX      TruthValue 
    MAX-ACCESS  read-only
    STATUS      current
    DESCRIPTION
            "If true, this parameter indicates the source is exceeding
            specified peak data rate for a traffic stream over the 
            Observation period."
    ::= { ocHnQosStreamStatisticsEntry 8 }

--
-- QoS Priority-based Statistics for PSD devices only
--

ocHnQosPriorityTrafficTable OBJECT-TYPE
    SYNTAX      SEQUENCE OF OcHnQosPriorityTrafficEntry
    MAX-ACCESS  not-accessible
    STATUS      current
    DESCRIPTION
            "This table contains a set of priority-based
            stream traffic statistics. It is indexed by the 
            Rotameter Observation Statistics table index. This
            correlates each row in this table with each row
            (i.e., observation) in the ROStatsTable."
    ::= { ocHnQos 5 }

ocHnQosPriorityTrafficEntry OBJECT-TYPE
    SYNTAX      OcHnQosPriorityTrafficEntry
    MAX-ACCESS  not-accessible
    STATUS      current
    DESCRIPTION
            "Each entry reflects traffic statistics
            for one priority."
    INDEX { ocHnQosROStatsIndex }
    ::= { ocHnQosPriorityTrafficTable 1 }

OcHnQosPriorityTrafficEntry ::=
    SEQUENCE {
        ocHnQosTrafficTotalBytesPriority0
            Counter32,
        ocHnQosTrafficTotalBytesPriority1
            Counter32,
        ocHnQosTrafficTotalBytesPriority2
            Counter32,
        ocHnQosTrafficTotalBytesPriority3
            Counter32,
        ocHnQosTrafficTotalBytesPriority4
            Counter32,
        ocHnQosTrafficTotalBytesPriority5
            Counter32,
        ocHnQosTrafficTotalBytesPriority6
            Counter32,
        ocHnQosTrafficTotalBytesPriority7
            Counter32
        }

ocHnQosTrafficTotalBytesPriority0 OBJECT-TYPE
    SYNTAX      Counter32
    MAX-ACCESS  read-only
    STATUS      current
    DESCRIPTION
            "Total number of bytes of all strictly prioritized
            flows interpreted as TrafficImportanceNumber '0' 
            during the Observation period."
    ::= { ocHnQosPriorityTrafficEntry 1 }

ocHnQosTrafficTotalBytesPriority1 OBJECT-TYPE
    SYNTAX      Counter32
    MAX-ACCESS  read-only
    STATUS      current
    DESCRIPTION
            "Total number of bytes of all strictly prioritized
            flows interpreted as TrafficImportanceNumber '1' 
            during the Observation period."
    ::= { ocHnQosPriorityTrafficEntry 2 }

ocHnQosTrafficTotalBytesPriority2 OBJECT-TYPE
    SYNTAX      Counter32
    MAX-ACCESS  read-only
    STATUS      current
    DESCRIPTION
            "Total number of bytes of all strictly prioritized
            flows interpreted as TrafficImportanceNumber '2' 
            during the Observation period."
    ::= { ocHnQosPriorityTrafficEntry 3 }

ocHnQosTrafficTotalBytesPriority3 OBJECT-TYPE
    SYNTAX      Counter32
    MAX-ACCESS  read-only
    STATUS      current
    DESCRIPTION
            "Total number of bytes of all strictly prioritized
            flows interpreted as TrafficImportanceNumber '3' 
            during the Observation period."
    ::= { ocHnQosPriorityTrafficEntry 4 }

ocHnQosTrafficTotalBytesPriority4 OBJECT-TYPE
    SYNTAX      Counter32
    MAX-ACCESS  read-only
    STATUS      current
    DESCRIPTION
            "Total number of bytes of all strictly prioritized
            flows interpreted as TrafficImportanceNumber '4' 
            during the Observation period."
    ::= { ocHnQosPriorityTrafficEntry 5 }

ocHnQosTrafficTotalBytesPriority5 OBJECT-TYPE
    SYNTAX      Counter32
    MAX-ACCESS  read-only
    STATUS      current
    DESCRIPTION
            "Total number of bytes of all strictly prioritized
            flows interpreted as TrafficImportanceNumber '5' 
            during the Observation period."
    ::= { ocHnQosPriorityTrafficEntry 6 }

ocHnQosTrafficTotalBytesPriority6 OBJECT-TYPE
    SYNTAX      Counter32
    MAX-ACCESS  read-only
    STATUS      current
    DESCRIPTION
            "Total number of bytes of all strictly prioritized
            flows interpreted as TrafficImportanceNumber '6' 
            during the Observation period."
    ::= { ocHnQosPriorityTrafficEntry 7 }

ocHnQosTrafficTotalBytesPriority7 OBJECT-TYPE
    SYNTAX      Counter32
    MAX-ACCESS  read-only
    STATUS      current
    DESCRIPTION
            "Total number of bytes of all strictly prioritized
            flows interpreted as TrafficImportanceNumber '7' 
            during the Observation period."
    ::= { ocHnQosPriorityTrafficEntry 8 }

--
-- Static configuration parameters
--

--
-- Static PQoS Device Table 
--

ocHnStaticPQosConfiguration OBJECT IDENTIFIER ::= { ocHnQos 6 }

ocHnStaticPQosStatus OBJECT-TYPE
    SYNTAX      TruthValue
    MAX-ACCESS  read-write
    STATUS      current
    DESCRIPTION
            "This object enables or disables the function on the local
            device to create Static PQoS flows on the HN. Disabling
            Static PQoS does not interrupt existing flows but prevents
            new flows from being established. Static PQoS must only
            be enabled on one device in the HN to avoid creation of
            multiple duplicate PQoS flows between trusted devices
            in the HN."
    ::= { ocHnStaticPQosConfiguration 1 }

ocHnStaticPQosDeviceTable OBJECT-TYPE
    SYNTAX      SEQUENCE OF OcHnStaticPQosDeviceEntry
    MAX-ACCESS  not-accessible
    STATUS      current
    DESCRIPTION
            "This table contains the MAC addresses of devices trusted
            to participate in Static PQoS flows. Any devices in this
            table may be paired to establish PQoS flows.  No traffic 
            policy policing is expected for any of these flows. The
            table contents must be persistent through reboots. The
            table must support at least 15 entries. The application
            software should update the state of its view of 
            the current network topology and PQoS status at 
            least once per minute in order to determine if a 
            PQoS flow needs to be re-established following a 
            device reboot or some other event. The application 
            software uses the MIB and the current network topology
            to set up / update /delete PQoS flows. Care must be taken
            when populating the Static PQoS Device Table to ensure
            multiple devices that support the application software do
            not create duplicate PQoS flows between trusted devices in
            the ocHnStaticPQosDeviceTable."
    ::= { ocHnStaticPQosConfiguration 2 }

ocHnStaticPQosDeviceEntry OBJECT-TYPE
    SYNTAX      OcHnStaticPQosDeviceEntry
    MAX-ACCESS  not-accessible
    STATUS      current
    DESCRIPTION
            "Each entry represents the MAC address eligible to
            participate in Static PQoS flows."
    INDEX { ocHnStaticPQosDeviceIndex }
    ::= { ocHnStaticPQosDeviceTable 1 }

OcHnStaticPQosDeviceEntry ::=
    SEQUENCE {
              ocHnStaticPQosDeviceIndex
                  Unsigned32,
              ocHnStaticPQosDeviceRowStatus
                  RowStatus,
              ocHnStaticPQosDeviceActive
                  TruthValue,
              ocHnStaticPQosDeviceMACAddress
                  MacAddress
             }

ocHnStaticPQosDeviceIndex OBJECT-TYPE
    SYNTAX      Unsigned32 (1..4294967295)
    MAX-ACCESS  not-accessible
    STATUS      current
    DESCRIPTION
            "Table Index."
    ::= { ocHnStaticPQosDeviceEntry 1 }

ocHnStaticPQosDeviceRowStatus OBJECT-TYPE
    SYNTAX      RowStatus
    MAX-ACCESS  read-create
    STATUS      current
    DESCRIPTION
            "A conceptual row cannot be active until the
            ocHnStaticPQosDeviceMACAddress is configured with a 
            MAC address."
    ::= { ocHnStaticPQosDeviceEntry 2 }

ocHnStaticPQosDeviceActive OBJECT-TYPE
    SYNTAX      TruthValue
    MAX-ACCESS  read-create
    STATUS      current
    DESCRIPTION
            "Setting this value to 'True' causes the device entry to be
            configured and activated. The default is 'False(2)' to
            prevent accidental configuration of flows when adding new
            MAC addresses not eligible for immediate use."
    ::= { ocHnStaticPQosDeviceEntry 3 }

ocHnStaticPQosDeviceMACAddress OBJECT-TYPE
    SYNTAX      MacAddress
    MAX-ACCESS  read-create
    STATUS      current
    DESCRIPTION
            "Set this value to indicate the MAC address of the
            PQoS device."
    ::= { ocHnStaticPQosDeviceEntry 4 }

--
-- Device addressing and operational status information
--

ocHnDevInterfaceStatus OBJECT IDENTIFIER ::= { ocHnMibObjects 4 }

ocHnDevInterfaceConfigTable OBJECT-TYPE  
    SYNTAX      SEQUENCE OF OcHnDevInterfaceConfigEntry
    MAX-ACCESS  not-accessible
    STATUS      current
    DESCRIPTION
            "This table augments the ifTable for each HN interface.
            It provides the mechanism for modifying and displaying
            interface characteristics not addressed by the IETF 
            ifTable. The index values will serve as an external index
            to the ocHnDevStatus tables."
    ::= { ocHnDevInterfaceStatus 1 }

ocHnDevInterfaceConfigEntry OBJECT-TYPE
    SYNTAX      OcHnDevInterfaceConfigEntry
    MAX-ACCESS  not-accessible
    STATUS      current
    DESCRIPTION
            "Each entry describes an interface for a specific
            technology."
    INDEX { ifIndex }
    ::= { ocHnDevInterfaceConfigTable 1 }

OcHnDevInterfaceConfigEntry ::=
    SEQUENCE {
        ocHnDevInterfaceConfigMaxPowerLevel
            Integer32,
        ocHnDevInterfaceConfigPowerUnits
            PowerUnit, 
        ocHnDevInterfaceConfigMaxParameterizedBandwidth
            Unsigned32,
        ocHnDevInterfaceConfigEnableEncryption
            INTEGER,
        ocHnDevInterfaceConfigEncryptionPassphrase
            SnmpAdminString
        }

ocHnDevInterfaceConfigMaxPowerLevel OBJECT-TYPE
    SYNTAX      Integer32
    MAX-ACCESS  read-write
    STATUS      current
    DESCRIPTION
            "Maximum power level used by an RSD Technology node.
            This level is combined with the measurement units
            defined in ocHnDevInterfaceConfigPowerUnits."
    ::= { ocHnDevInterfaceConfigEntry 2 }

ocHnDevInterfaceConfigPowerUnits OBJECT-TYPE
    SYNTAX      PowerUnit
    MAX-ACCESS  read-only
    STATUS      current
    DESCRIPTION
            "Reports the power units of measurement/reporting 
            in ocHnDevInterfacePowerUnits used by the RSD 
            technology on the interface being
            reported."
    ::= { ocHnDevInterfaceConfigEntry 3 }

ocHnDevInterfaceConfigMaxParameterizedBandwidth OBJECT-TYPE
    SYNTAX      Unsigned32
    MAX-ACCESS  read-write
    STATUS      current
    DESCRIPTION
            "This object requests the maximum bandwidth, as a 
            percentage of total bandwidth, to be made available for
            parameterized traffic streams. The actual bandwidth made
            available for parameterized streams is represented by 
            ocHnDevInterfaceStatusMaxParameterizedBandwidth object.
            This configuration takes effect only if the node
            is the Layer2Scheduler for the RSD Technology interface 
            (i.e., if the ocHnDevInterfaceStatusLayer2Scheduler object
            is set to true on this node)."
    ::= { ocHnDevInterfaceConfigEntry 4 }

ocHnDevInterfaceConfigEnableEncryption OBJECT-TYPE
    SYNTAX      INTEGER
                {
                enabled(1),
                disabled(2)
                }
    MAX-ACCESS  read-write
    STATUS      current
    DESCRIPTION
            "A Boolean parameter used to enable or disable privacy
            (link layer encryption) on the RSD Technology. The default
            is disabled(2)."
    ::= { ocHnDevInterfaceConfigEntry 5 }

ocHnDevInterfaceConfigEncryptionPassphrase OBJECT-TYPE
    SYNTAX      SnmpAdminString (SIZE (24 | 32) )
    MAX-ACCESS  read-write
    STATUS      current
    DESCRIPTION
            "A Password or a key used for encrypting data sent over
            the RSD Technology using technology-specific encryption
            algorithm." 
    ::= { ocHnDevInterfaceConfigEntry 6 }

--
-- Device Network Operating Status
--

ocHnDevInterfaceStatusTable OBJECT-TYPE
    SYNTAX      SEQUENCE OF OcHnDevInterfaceStatusEntry
    MAX-ACCESS  not-accessible
    STATUS      current
    DESCRIPTION
            "This table tracks and reports current network
            related attributes for each interface (e.g., MAC)."
    ::= { ocHnDevInterfaceStatus 2 }

ocHnDevInterfaceStatusEntry OBJECT-TYPE
    SYNTAX      OcHnDevInterfaceStatusEntry
    MAX-ACCESS  not-accessible
    STATUS      current
    DESCRIPTION
            "Each entry associates the network operational
            assignments for each interface."
    INDEX { ifIndex }
    ::= { ocHnDevInterfaceStatusTable 1 }

OcHnDevInterfaceStatusEntry ::=
    SEQUENCE {
        ocHnDevInterfaceStatusTxBroadcastRate
            Unsigned32,
        ocHnDevInterfaceStatusTxBroadcastLevel
            Tenths,
        ocHnDevInterfaceStatusMaxTxPowerLevel
            Tenths,
        ocHnDevInterfaceStatusPowerUnits
            PowerUnit,
        ocHnDevInterfaceStatusMaxParameterizedBandwidth
            Unsigned32,
        ocHnDevInterfaceStatusLayer2Scheduler
            TruthValue
              }

ocHnDevInterfaceStatusTxBroadcastRate OBJECT-TYPE
    SYNTAX      Unsigned32
    UNITS       "bits/sec"
    MAX-ACCESS  read-only
    STATUS      current
    DESCRIPTION
            "Broadcast transmit rate (bits/sec) for this interface."
    ::= { ocHnDevInterfaceStatusEntry 1 }

ocHnDevInterfaceStatusTxBroadcastLevel OBJECT-TYPE
    SYNTAX      Tenths
    MAX-ACCESS  read-only
    STATUS      current
    DESCRIPTION
            "The power level used for transmission of broadcast
            messages by the RSD node reported in units defined by
            ocHnDevInterfaceStatusPowerUnits."
    ::= { ocHnDevInterfaceStatusEntry 2 }

ocHnDevInterfaceStatusMaxTxPowerLevel OBJECT-TYPE
    SYNTAX      Tenths
    MAX-ACCESS  read-only
    STATUS      current
    DESCRIPTION
            "The absolute maximum power level that a node 
            is capable of transmitting. The power units
            are defined in ocHnDevInterfaceStatusPowerUnits."
    ::= { ocHnDevInterfaceStatusEntry 3 }

ocHnDevInterfaceStatusPowerUnits OBJECT-TYPE
    SYNTAX      PowerUnit
    MAX-ACCESS  read-only
    STATUS      current
    DESCRIPTION
            "Reports the power units of measurement/reporting 
            in ocHnDevInterfacePowerUnits used by the RSD 
            technology on the interface being reported."
    ::= { ocHnDevInterfaceStatusEntry 4 }

ocHnDevInterfaceStatusMaxParameterizedBandwidth OBJECT-TYPE
    SYNTAX      Unsigned32
    MAX-ACCESS  read-only
    STATUS      current
    DESCRIPTION
            "The actual bandwidth, as a percentage of total, that can
            be utilized for reservation-based (parameterized)
            traffic streams. A value of '0' should be reported if 
            this node is not a layer2scheduler for the RSD Technology
            interface (i.e., if the 
            ocHnDevInterfaceStatusLayer2Scheduler
            object is set to false on this node)."
    ::= { ocHnDevInterfaceStatusEntry 5 }

ocHnDevInterfaceStatusLayer2Scheduler OBJECT-TYPE
    SYNTAX      TruthValue 
    MAX-ACCESS  read-only
    STATUS      current
    DESCRIPTION
            "This Boolean parameter indicates whether this particular
            node is a layer-2 scheduler."
    ::= { ocHnDevInterfaceStatusEntry 6 }

--
-- Logical Device Connection Table
--

ocHnDevConnectionTable OBJECT-TYPE
    SYNTAX      SEQUENCE OF OcHnDevConnectionEntry
    MAX-ACCESS  not-accessible
    STATUS      current
    DESCRIPTION
            "This table defines the logical connections, by MAC,
            of all the devices known to this interface."
    ::= { ocHnDevInterfaceStatus 3 }

ocHnDevConnectionEntry OBJECT-TYPE
    SYNTAX      OcHnDevConnectionEntry
    MAX-ACCESS  not-accessible
    STATUS      current
    DESCRIPTION
            "Each entry associates the network operational
            attributes of the connections for each interface."
    INDEX { ifIndex, ocHnDevConnectionIndex }
    ::= { ocHnDevConnectionTable 1 }

OcHnDevConnectionEntry ::=
    SEQUENCE {
        ocHnDevConnectionIndex
            Unsigned32,
        ocHnDevConnectionDestMac
            MacAddress,
        ocHnDevConnectionRxLinkRate
            Unsigned32,
        ocHnDevConnectionRxModulationType
            SnmpAdminString,
        ocHnDevConnectionRxBroadcastRate
            Unsigned32,
        ocHnDevConnectionRxSignalStrength
            Tenths,
        ocHnDevConnectionTxUnicastLevel
            Tenths,
        ocHnDevConnectionPowerUnits
            PowerUnit,
        ocHnDevConnectionTxLinkRate
            Unsigned32,
        ocHnDevConnectionTxModulationType
            SnmpAdminString
        }

ocHnDevConnectionIndex OBJECT-TYPE
    SYNTAX      Unsigned32 (1..4294967295)
    MAX-ACCESS  not-accessible
    STATUS      current
    DESCRIPTION
            "Secondary index of the connection table."
    ::= { ocHnDevConnectionEntry 1 }


ocHnDevConnectionDestMac OBJECT-TYPE
    SYNTAX      MacAddress
    MAX-ACCESS  read-only
    STATUS      current
    DESCRIPTION
            "MAC of other device if visible to
            this device."
    ::= { ocHnDevConnectionEntry 2 }

ocHnDevConnectionRxLinkRate OBJECT-TYPE
    SYNTAX      Unsigned32
    UNITS       "bits/sec"
    MAX-ACCESS  read-only
    STATUS      current
    DESCRIPTION
            "PHY reception rate (bits/sec) on this interface
            from the node identified by its MAC address."
    ::= { ocHnDevConnectionEntry 3 }

ocHnDevConnectionRxModulationType OBJECT-TYPE
    SYNTAX      SnmpAdminString
    MAX-ACCESS  read-only
    STATUS      current
    DESCRIPTION
            "Type of modulation currently being used by an
            interface on this node for reception from the
            node identified by MAC address. A value is required
            only if this is an RF technology-based connection.
            Non-RF interfaces should report 'n/a'."
    ::= { ocHnDevConnectionEntry 4 }

ocHnDevConnectionRxBroadcastRate OBJECT-TYPE
    SYNTAX      Unsigned32
    UNITS       "bits/sec"
    MAX-ACCESS  read-only
    STATUS      current
    DESCRIPTION
            "Receive rate (bits/sec) at this RSD Interface for
            broadcasts initiated by the logically connected node
            identified by the destination MAC Address in
            this table entry."
    ::= { ocHnDevConnectionEntry 5 }

ocHnDevConnectionRxSignalStrength OBJECT-TYPE
    SYNTAX      Tenths
    MAX-ACCESS  read-only
    STATUS      current
    DESCRIPTION
            "The signal strength received at this 
            interface from the associated node identified by 
            the MAC address. The power units are defined 
            in ocHnDevConnectionPowerUnits "
    ::= { ocHnDevConnectionEntry 6 }

ocHnDevConnectionTxUnicastLevel OBJECT-TYPE
    SYNTAX      Tenths
    MAX-ACCESS  read-only
    STATUS      current
    DESCRIPTION
            "The power level used for transmission of unicast
            messages by the RSD node reported in units 
            defined in ocHnDevConnectionPowerUnits for
            this interface."
    ::= { ocHnDevConnectionEntry 7 }

ocHnDevConnectionPowerUnits OBJECT-TYPE
    SYNTAX      PowerUnit
    MAX-ACCESS  read-only
    STATUS      current
    DESCRIPTION
            "Reports the power units of measurement/reporting 
            in ocHnDevInterfacePowerUnits used by the RSD 
            technology on the interface being
            reported."
    ::= { ocHnDevConnectionEntry 8 }

ocHnDevConnectionTxLinkRate OBJECT-TYPE
    SYNTAX      Unsigned32
    UNITS       "bits/sec"
    MAX-ACCESS  read-only
    STATUS      current
    DESCRIPTION
            "PHY transmission rate (bits/sec) from this interface
            to the node identified by MAC addresses."
    ::= { ocHnDevConnectionEntry 9 }

ocHnDevConnectionTxModulationType OBJECT-TYPE
    SYNTAX      SnmpAdminString
    MAX-ACCESS  read-only
    STATUS      current
    DESCRIPTION
            "The modulation type currently employed by this
            interface while transmitting to the node
            identified by its MAC address. A value is required
            only if this is an RF technology-based connection.
            Non-RF interfaces should report 'n/a'."
    ::= { ocHnDevConnectionEntry 10 }

--
-- Network Configuration Settings   --
--
 
ocHnNetConfig OBJECT IDENTIFIER ::= { ocHnMibObjects 5 }
 
ocHnNetConfigViewPrimaryOutputPort  OBJECT-TYPE
    SYNTAX      TruthValue
    MAX-ACCESS  read-write
    STATUS      current
    DESCRIPTION
            "This Boolean parameter indicates whether the view primary
            output port content item is published in CDS.  The default
            value of false indicates do not publish."  
    ::= { ocHnNetConfig 1 }

ocHnNetConfigViewPrimaryOutputPortOrgID  OBJECT-TYPE
    SYNTAX      Unsigned32
    MAX-ACCESS  read-write
    STATUS      current
    DESCRIPTION
            "This 32 bit parameter indicates the organization ID of an application
             That will be given permission to write properties in the VPOP content
             item.  The default value of 0 indicates no write access by an
             organization."
    ::= { ocHnNetConfig 2 }

ocHnNetConfigPersistentLinkLocalAddress OBJECT-TYPE
    SYNTAX      TruthValue
    MAX-ACCESS  read-write
    STATUS      current
    DESCRIPTION
            "This Boolean parameter indicates whether persistent local link address
             handling is enabled or disabled. The default value os false indicated
             disabled."
    ::= { ocHnNetConfig 3 }

--

ocHnConformance    OBJECT IDENTIFIER ::= { ocHnMibModule 3 }
ocHnMIBCompliances OBJECT IDENTIFIER ::= { ocHnConformance 1 }
ocHnMIBGroups      OBJECT IDENTIFIER ::= { ocHnConformance 2 }

-- Compliance statements

ocHnMIBCompliance MODULE-COMPLIANCE
    STATUS      current
    DESCRIPTION
            "The requirements for conformance to the OpenCable
            Home Networking MIB."
    MODULE -- this module
    MANDATORY-GROUPS {
                     ocHnHomeNetworkStatusGroup,
                     ocHnGenericDevInterfaceGroup,
                     ocHnNetConfigGroup
                     }

    GROUP  ocHnRotameterConfigGroup
    DESCRIPTION 
            "This group is an optional implementation."

    GROUP ocHnQosTrafficDescInfo
    DESCRIPTION
            "This group is an optional implementation."

    GROUP ocHnQosGroup
    DESCRIPTION
            "This group is an optional implementation."
    ::= { ocHnMIBCompliances 1 }

ocHnHomeNetworkStatusGroup OBJECT-GROUP
    OBJECTS     {
                ocHnRsdManagerImportanceNumber,
                ocHnRsdManagerPreferredStatus,
                ocHnDevUpnpServiceType,
                ocHnDevUpnpServiceAvailable,
                ocHnDevSupportedChannelLastOperatingFreq,
                ocHnDevSupportedChannelInUse,
                ocHnDevSupportedChannelFrequency,
                ocHnDevSupportedChannelEligible,
                ocHnDevPropertiesFriendlyName
                }
    STATUS      current
    DESCRIPTION
            "Defines the objects used to report the status
            of the home network."
    ::= { ocHnMIBGroups 1 }

ocHnGenericDevInterfaceGroup OBJECT-GROUP
    OBJECTS     {
                ocHnDevInterfaceConfigMaxPowerLevel,
                ocHnDevInterfaceConfigPowerUnits,
                ocHnDevInterfaceConfigMaxParameterizedBandwidth,
                ocHnDevInterfaceConfigEnableEncryption,
                ocHnDevInterfaceConfigEncryptionPassphrase,
                ocHnDevInterfaceStatusLayer2Scheduler,
                ocHnDevInterfaceStatusTxBroadcastLevel,
                ocHnDevInterfaceStatusTxBroadcastRate,
                ocHnDevInterfaceStatusMaxTxPowerLevel,
                ocHnDevInterfaceStatusPowerUnits,
                ocHnDevInterfaceStatusMaxParameterizedBandwidth,
                ocHnDevConnectionDestMac,
                ocHnDevConnectionRxLinkRate,
                ocHnDevConnectionRxModulationType,
                ocHnDevConnectionRxBroadcastRate,
                ocHnDevConnectionRxSignalStrength,
                ocHnDevConnectionPowerUnits,
                ocHnDevConnectionTxUnicastLevel,
                ocHnDevConnectionTxLinkRate,
                ocHnDevConnectionTxModulationType
                }
    STATUS      current
    DESCRIPTION
            "The objects common to all the OCHN interfaces."
    ::= { ocHnMIBGroups 2 }

ocHnRotameterConfigGroup OBJECT-GROUP
    OBJECTS     {
                ocHnRotameterConfigRowStatus,
                ocHnRotameterConfigQosSegmentId,
                ocHnRotameterConfigObservationActive,
                ocHnRotameterConfigEndpointMacAddress,
                ocHnRotameterConfigPeriod, 
                ocHnRotameterConfigMonitorResolutionPeriod,
                ocHnPerStreamRotameterConfigRowStatus,
                ocHnPerStreamRotameterConfigLayer2StreamId,
                ocHnPerStreamRotameterConfigTrafficHandle,
                ocHnPerStreamRotameterConfigObservationActive
                }
    STATUS      current
    DESCRIPTION
            "The collection of objects used to create one or more
             Rotameter configurations that may be activated via
             SNMP."
    ::= { ocHnMIBGroups 3 }

ocHnQosTrafficDescInfo OBJECT-GROUP
    OBJECTS     {
                ocHnQosStreamsInfoCollectionTrigger,
                ocHnQosTrafficQDMacAddress,
                ocHnQosTrafficHandle,
                ocHnQosTrafficNetworkAddressType,
                ocHnQosTrafficSourceAddress,
                ocHnQosTrafficSourcePort,
                ocHnQosTrafficDestinationAddress,
                ocHnQosTrafficDestinationPort, 
                ocHnQosTrafficIpProtocol,
                ocHnQosTrafficV3TrafficIdSourceUuid,
                ocHnQosTrafficV3TrafficIdDestinationUuid,
                ocHnQosTrafficMediaServerConnectionId,
                ocHnQosTrafficMediaRendererConnectionId, 
                ocHnQosTrafficLeaseTime, 
                ocHnQosTrafficCritical, 
                ocHnQosTrafficUserName, 
                ocHnQosTrafficVendorApplicationName, 
                ocHnQosTrafficPortName, 
                ocHnQosTrafficServiceProviderServiceName, 
                ocHnQosTrafficCpName,
                ocHnQosTspec,
                ocHnQosActiveTspec,
                ocHnQosTspecTrafficClass,
                ocHnQosTspecReqQosType,
                ocHnQosTspecDataRate,
                ocHnQosTspecPeakDataRate,
                ocHnQosTspecMaxBurstSize,
                ocHnQosTspecMaxPacketSize,
                ocHnQosTspecE2EMaxDelayHigh,
                ocHnQosTspecE2EMaxJitter,
                ocHnQosPolicyRowStatus,
                ocHnQosPolicyIpAddressType, 
                ocHnQosPolicySourceAddressUpLimit, 
                ocHnQosPolicySourceAddressLowLimit, 
                ocHnQosPolicySourcePortUpLimit, 
                ocHnQosPolicySourcePortLowLimit, 
                ocHnQosPolicyDestinationAddressUpLimit, 
                ocHnQosPolicyDestinationAddressLowLimit, 
                ocHnQosPolicyDestinationPortUpLimit, 
                ocHnQosPolicyDestinationPortLowLimit, 
                ocHnQosPolicyIpProtocolUpLimit,
                ocHnQosPolicyIpProtocolLowLimit, 
                ocHnQosPolicyTrafficClass, 
                ocHnQosPolicyPeakDataRateUpLimit, 
                ocHnQosPolicyPeakDataRateLowLimit,
                ocHnQosPolicyMeanDataRateUpLimit, 
                ocHnQosPolicyMeanDataRateLowLimit,
                ocHnQosPolicyMaxBurstSizeUpLimit, 
                ocHnQosPolicyMaxBurstSizeLowLimit,
                ocHnQosPolicyE2EMaxDelayHighLimit, 
                ocHnQosPolicyE2EMaxDelayLowLimit,
                ocHnQosPolicyBoundaryAddressType, 
                ocHnQosPolicyBoundarySourceAddressUpLimit, 
                ocHnQosPolicyBoundarySourceAddressLowLimit, 
                ocHnQosPolicyBoundaryDestinationAddressUpLimit, 
                ocHnQosPolicyBoundaryDestinationAddressLowLimit,
                ocHnQosPolicyUserName, 
                ocHnQosPolicyVendorApplicationName, 
                ocHnQosPolicyPortName, 
                ocHnQosPolicyServiceProviderServiceName,
                ocHnQosPolicyCriticalFlag,
                ocHnQosPolicyRequestedQosType, 
                ocHnQosPolicyStartTime,
                ocHnQosPolicyEndTime, 
                ocHnQosPolicyTrafficLeaseTimeUpValue,
                ocHnQosPolicyTrafficLeaseTimeLowValue,
                ocHnQosPolicyRuleType,
                ocHnQosPolicyRulePriority,
                ocHnQosPolicyTrafficImportanceNumber,
                ocHnQosPolicyUserImportanceNumber
                }
    STATUS      current
    DESCRIPTION
            "List of objects used to acquire QOS traffic attributes
            as well as set QOS Policies."
    ::= { ocHnMIBGroups 4 }

ocHnQosGroup OBJECT-GROUP
    OBJECTS     {
                ocHnQosROStatsIdentifier,
                ocHnQosROStatsMacAddress,
                ocHnQosROStatsObservationMacAddress,
                ocHnQosROStatsQosSegmentId,
                ocHnQosROStatsTotalTrafficBytes,
                ocHnQosROStatsTotalParameterizedBytes,
                ocHnQosROStatsTotalParameterizedPackets,
                ocHnQosROStatsTotalParameterizedPacketsDropped,
                ocHnQosROStatsReportingDateAndTime,
                ocHnQosROStatsObservationPeriod,
                ocHnQosROStatsMonitorResolutionPeriod,
                ocHnQosStreamStatisticsLayer2StreamId,
                ocHnQosStreamStatisticsPktsTransmitted,
                ocHnQosStreamStatisticsPktsReceived,
                ocHnQosStreamStatisticsErrorPktsDropped,
                ocHnQosStreamStatisticsBytesTransmitted,
                ocHnQosStreamStatisticsBytesReceived,
                ocHnQosStreamStatisticsTrafficHandle,
                ocHnQosStreamStatisticsPeakDataRateViolations,
                ocHnQosTrafficTotalBytesPriority0,
                ocHnQosTrafficTotalBytesPriority1,
                ocHnQosTrafficTotalBytesPriority2,
                ocHnQosTrafficTotalBytesPriority3,
                ocHnQosTrafficTotalBytesPriority4,
                ocHnQosTrafficTotalBytesPriority5,
                ocHnQosTrafficTotalBytesPriority6,
                ocHnQosTrafficTotalBytesPriority7,
                ocHnStaticPQosStatus,
                ocHnStaticPQosDeviceRowStatus,
                ocHnStaticPQosDeviceActive, 
                ocHnStaticPQosDeviceMACAddress
                }
    STATUS      current
    DESCRIPTION
            "Parameterized and prioritized traffic flow objects."
    ::= { ocHnMIBGroups 5 }
    
ocHnNetConfigGroup OBJECT-GROUP
    OBJECTS     {
              ocHnNetConfigViewPrimaryOutputPort 
                }
    STATUS      current
    DESCRIPTION
            "HN configuration parameters."
    ::= { ocHnMIBGroups 6 }
    

END
